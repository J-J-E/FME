FME workspace WorkspaceExaminer.fmw
Title: Workspace Examiner
Description: Provides an easy to use framework for evaulating FME Workspaces
Usage: 1. Set Reporting Parameters
    Choose Main folder - this is the folder contianing workspaces you want to evaluate 
    Include workspaces in subfolders - enabling this will allow recursion into all subfolders of the main folder 
    Directories to ignore - this is a regex filter allowing the user to specify one or more directories to ignore (Ex. Backup|Archive as a parameter would make this process ignore all directories that have backup OR archive in the file path) 
    Target Directories/workspace - regex clause to specify target directories. (Ex. You have 10 workspaces prefixed with "GDM_" and are only interested in those passing GDM_ as a parameter will report on only those) 
    Report Directory - Specify directory location to write reports. If not location is specified, the process will create a new foldercalled "WorkspaceReports" in the same folder that the Workspace is running in
    Individual reports - leaving this unchecked will generate one HUGE report. 
2. Generate Workspace Statistics
    Choose Report Type - one or more report types may be selected. 
    Genericize transformers - If this is checked, all transformers wil be grouped into categoriies of "Transformers, Reader, Writers". Leaving this unchecked will produce a lengthy report with specific transformer names
3. Transformers
    Custom Transformers - Outputs table of custom transformers used in workspaces and whether they are linked or embedded 
    Upgradeable Transformers - Identify transformers in workspace that need to be upgraded. *Note, this will also look at ALL transformer defenitions saved in a workspace, regardless of if they exist in the cavas. You may encounter a case where the process says you have ungradeable transformers and you cannot find them in the navigator pane. In this scenarior, the are most likely in the Transformer gallery and the defeniton of a custom transformer not currently being used has been saved.
4. Workspace History / Description
    Option to generate report for workspaces missing history 
    Option to generate report for workspaces missing description
5. Input/Output Paths 
    Option to generate report 
    Option to report filepaths that include an FME Parameter 
    Option to check if input file path exists 
    Option to check is output file path exists 
6. Wildcard Search
    Provides multiple options for searching including Feature Types, AttributeNames, and Published Paramters
     Multiple values can searched for together by separating with with the pipe character |
    Do not include leading/trailing spaces unless the space is desired in the search
6.1. Input/Output Features
    Option to search in inputs 
    Option to search in outputs 
    Wildcard search string. (Ex. If you wanted to find every process using a database tables called "Counties" you could put the string Counties into the search box)
6.2. AttributeName/Types
    Option to search for attributes in Readers
    Option to search for attributes in Writers
    Option to search for attributes in Transformers
    Wildcard search string. (Ex. If you wanted to find every FME workspace that had a specific attribute/column name and know which transformer was using that attribute )
6.3.Published Parameters
    Option to search in published parameters
    Option to search in published parameters default value
    Wildcard search string. (Ex. Your company has switched domains and your email address has changed: You could search every workspace to find each instance of a parameter "EmailTo" or use this to search for the default value of "username@domain.com" where username if your email and the domain is your old email domain address. OR perhaps this is a SQLConn parameter, and you need to update the SQL connection in each workspace.)
History: 2021/12/01,JJE,Added Description/History/Help; Altered Log File Location,2021/12/01,JJE,Enhanced Upgradeable Xformer detection to include linked custom transformers. Old Process collapsed into bookmark and saved for reference.

Parameters:
- PARAMETER =
- PARAMETER_2 =
- p_FeatureWildcard =
- p_FolderRecursion =
- p_GenerateDescription =
- p_GenerateHistory =
- p_GenerateStatistics =
- p_HistoryDescription =
- p_IdentifyFMEParamPAths =
- p_IdentifyNonUNC =
- p_IndividualReports =
- p_NonUncPaths =
- p_ParentDirectory =
- p_ReportLocation =
- p_Reporting =
- p_StatsGenericizeXFormerNames =
- p_StatsMessage =
- p_Transformers =
- p_WorkspaceStatistics =
- p_attrSearch_Reader =
- p_attrSearch_Transformer =
- p_attrSearch_Writer =
- p_attrSearch_wildcard =
- p_attributeSearch_2 =
- p_checkExistence_inputs =
- p_checkExistence_ouputs =
- p_customXformer =
- p_customXformerGroup =
- p_customXformerWildcard =
- p_ignoreDirectories =
- p_inputSearch =
- p_message =
- p_msgParams_3 =
- p_paramsearch_wildcard =
- p_pubparamSearch =
- p_pubparam_defaultvalue =
- p_pubparam_name =
- p_searchInputs =
- p_searchOutputs =
- p_upgradeable =
- p_wilcardFilePath =
- p_wildcardSearches =

Note: Read FMW/FMX files in bulk, expose all ports for routing to various bookmarks
FeatureReader_3
    ATTRIBUTES = Annotations,"workspace_id,custom_transformer_parent_name,annotation_id,annotation,annotation_type,fme_geometry{0},fme_dataset,fme_basename,fme_feature_type",Bookmarks,"workspace_id,custom_transformer_parent_name,bookmark_id,bookmark_name,bookmark_description,fme_geometry{0},fme_dataset,fme_basename,fme_feature_type",Breakpoints,"workspace_id,custom_transformer_parent_name,breakpoint_id,breakpoint_name,breakpoint_condition,breakpoint_test_clause,breakpoint_enabled,fme_geometry{0},fme_dataset,fme_basename,fme_feature_type",Connections,"workspace_id,custom_transformer_parent_name,connection_id,connection_source_id,connection_target_id,connection_source_port_desc,connection_target_port_desc,connection_enabled,connection_execution_index,connection_hidden,fme_geometry{0},fme_dataset,fme_basename,fme_feature_type",FeatureTypeFormatAttributes,"workspace_id,feature_type_id,format_attribute_name,format_attribute_type,fme_geometry{0},fme_dataset,fme_basename,fme_feature_type",FeatureTypeParameters,"workspace_id,feature_type_id,feature_type_parameter_name,feature_type_parameter_value,fme_geometry{0},fme_dataset,fme_basename,fme_feature_type",FeatureTypeUserAttributes,"workspace_id,feature_type_id,user_attribute_name,user_attribute_type,user_attribute_exposed,fme_geometry{0},fme_dataset,fme_basename,fme_feature_type",FileProperties,"workspace_id,file_path,file_size,creation_date,modified_date,last_run_date,fme_geometry{0},fme_dataset,fme_basename,fme_feature_type",PublishedParameters,"workspace_id,custom_transformer_parent_name,published_parameter_name,published_parameter_type,published_parameter_default_value,fme_geometry{0},fme_dataset,fme_basename,fme_feature_type",ReaderFeatureTypes,"workspace_id,reader_id,feature_type_id,reader_feature_type_qualifier,reader_feature_type_name,reader_feature_type_possible_geometries,reader_feature_type_enabled,fme_geometry{0},fme_dataset,fme_basename,fme_feature_type",ReaderHistogram,"workspace_id,reader_type,reader_count,fme_geometry{0},fme_dataset,fme_basename,fme_feature_type",ReaderParameters,"workspace_id,reader_id,reader_parameter_name,reader_parameter_value,fme_geometry{0},fme_dataset,fme_basename,fme_feature_type",Readers,"workspace_id,reader_id,reader_name,reader_keyword,reader_type,source_dataset,reader_enabled,reader_generate_build_number,fme_geometry{0},fme_dataset,fme_basename,fme_feature_type",Statistics,"workspace_id,num_published_parameters,num_annotations,num_bookmarks,num_breakpoints,num_readers,num_reader_feature_types,num_writers,num_writer_feature_types,num_transformers,num_custom_transformers,num_out_of_date_transformers,num_connections,fme_geometry{0},fme_dataset,fme_basename,fme_feature_type",TransformerHistogram,"workspace_id,transformer_type,transformer_count,fme_geometry{0},fme_dataset,fme_basename,fme_feature_type",TransformerOutputPortAttributes,"workspace_id,custom_transformer_parent_name,transformer_id,transformer_output_port_id,transformer_output_port_attribute_name,transformer_output_port_attribute_constant_value,transformer_output_port_attribute_enabled,fme_geometry{0},fme_dataset,fme_basename,fme_feature_type",TransformerOutputPorts,"workspace_id,custom_transformer_parent_name,transformer_id,transformer_output_port_id,transformer_output_port_name,fme_geometry{0},fme_dataset,fme_basename,fme_feature_type",TransformerParameters,"workspace_id,custom_transformer_parent_name,transformer_id,transformer_parameter_name,transformer_parameter_value,fme_geometry{0},fme_dataset,fme_basename,fme_feature_type",Transformers,"workspace_id,custom_transformer_parent_name,transformer_id,transformer_name,transformer_type,transformer_aliases,current_transformer_version,max_transformer_version,transformer_enabled,transformer_last_edit_build_number,fme_geometry{0},fme_dataset,fme_basename,fme_feature_type",WorkspaceProperties,"workspace_id,workspace_name,workspace_description,modified_build_number,category,help,history,requirement,requirements_flag,legal,use_markdown,fme_geometry{0},fme_dataset,fme_basename,fme_feature_type",WriterFeatureTypes,"workspace_id,writer_id,feature_type_id,writer_feature_type_qualifier,writer_feature_type_name,writer_feature_type_possible_geometries,writer_feature_type_enabled,fme_geometry{0},fme_dataset,fme_basename,fme_feature_type",WriterHistogram,"workspace_id,writer_type,writer_count,fme_geometry{0},fme_dataset,fme_basename,fme_feature_type",WriterParameters,"workspace_id,writer_id,writer_parameter_name,writer_parameter_value,fme_geometry{0},fme_dataset,fme_basename,fme_feature_type",Writers,"workspace_id,writer_id,writer_name,writer_keyword,writer_type,destination_dataset,writer_enabled,writer_generate_build_number,fme_geometry{0},fme_dataset,fme_basename,fme_feature_type"
    ATTR_ACCUM_MODE = Only Use Result
    COMBINE_GEOM = Use Result
    DATASET = @Value(path_windows)
    FMW_FMW_EXPOSE_FORMAT_ATTRS = fme_dataset,string fme_basename,string fme_feature_type,string
    FMW_USE_UNIQUE_IDS = yes
    FMW_USE_UNIQUE_WORKSPACE_IDS = yes
    FORMAT = FMW
    OUTPUT_FEATURES_DISPLAY = Schema and Data Features
    FeatureTypeUserAttributes -> Junction_6
    PublishedParameters -> Junction_30
    ReaderFeatureTypes -> Junction_4
    ReaderFeatureTypes -> Junction_24
    ReaderHistogram -> Junction_16
    ReaderParameters -> Junction_13
    Readers -> Junction_9
    Readers -> Junction_3
    TransformerHistogram -> Junction_20
    TransformerOutputPortAttributes -> Junction_27
    TransformerParameters -> Junction
    TransformerParameters -> Junction_21
    Transformers -> Junction_19
    Transformers -> Junction_25
    Transformers -> Junction_7
    Transformers -> Junction_28
    WorkspaceProperties -> Junction_8
    WriterFeatureTypes -> Junction_5
    WriterFeatureTypes -> Junction_26
    WriterHistogram -> Junction_18
    WriterParameters -> Junction_12
    Writers -> Junction_2
    Writers -> Junction_11
Note: ReaderHistogram
Junction_16
    -> GenerateDirectoryStatistics [ReaderHistogram]
Note: TransformerHistogram
Junction_20
    -> GenerateDirectoryStatistics [TransformerHistogram]
Note: WriterHistogram
Junction_18
    -> GenerateDirectoryStatistics [WriterHistogram]
GenerateDirectoryStatistics
    TRANSFORMER_TYPE = @Value(transformer_type)
    p_GenerateStatistics = $(p_GenerateStatistics)
    p_ParentDirectory = $(p_ParentDirectory)
    p_StatsGenericizeXFormerNames = $(p_StatsGenericizeXFormerNames)
    DirectoryStatisticsHTML -> TST_IndividualReport_7
Note: Transformers
Junction_25
    -> ListCustomTransformers [Transformers]
    -> IdentifyUpgradeableTransformers [Transformers]
ListCustomTransformers
    CUSTOM_TRANSFORMER_PARENT_NAME = @Value(custom_transformer_parent_name)
    FME_BASENAME = @Value(fme_basename)
    FME_DATASET = @Value(fme_dataset)
    TRANSFORMER_TYPE = @Value(transformer_type)
    p_customXformer = $(p_customXformer)
    p_customXformerWildcard = $(p_customXformerWildcard)
    CustomTransformersHTML -> TST_IndividualReport_7
IdentifyUpgradeableTransformers
    CURRENT_TRANSFORMER_VERSION = @Value(current_transformer_version)
    CUSTOM_TRANSFORMER_PARENT_NAME = @Value(custom_transformer_parent_name)
    FME_BASENAME = @Value(fme_basename)
    FME_DATASET = @Value(fme_dataset)
    MAX_TRANSFORMER_VERSION = @Value(max_transformer_version)
    p_upgradeable = $(p_upgradeable)
    UpgradeableTransformersHTML -> TST_IndividualReport_7
Note: Workspace Properties
Junction_8
    -> WorkspaceHistory [WorkspaceProperties]
    -> WorkspaceOverviews [WorkspaceProperties]
WorkspaceOverviews
    FME_BASENAME = @Value(fme_basename)
    FME_DATASET = @Value(fme_dataset)
    p_GenerateDescription = $(p_GenerateDescription)
    WorkspaceOverviewsHTML -> TST_IndividualReport_7
WorkspaceHistory
    FME_BASENAME = @Value(fme_basename)
    FME_DATASET = @Value(fme_dataset)
    HISTORY = @Value(history)
    p_GenerateHistory = $(p_GenerateHistory)
    WorkspaceHistoryHTML -> TST_IndividualReport_7
Note: Readers
Junction_9
    -> IdentifyPathTypes [Readers]
Note: TransformerParameters
Junction
    -> IdentifyPathTypes [TransformerParameters]
Note: Transformers
Junction_7
    -> IdentifyPathTypes [Transformers]
    -> IdentifyPathTypes [Transformers_2]
Note: Writers
Junction_2
    -> IdentifyPathTypes [Writers]
IdentifyPathTypes
    FME_BASENAME = @Value(fme_basename)
    FME_DATASET = @Value(fme_dataset)
    TRANSFORMER_ID = @Value(transformer_id)
    TRANSFORMER_PARAMETER_NAME = @Value(transformer_parameter_name)
    TRANSFORMER_TYPE = @Value(transformer_type)
    WORKSPACE_ID = @Value(workspace_id)
    p_IdentifyFMEParamPAths = $(p_IdentifyFMEParamPAths)
    p_IdentifyNonUNC = $(p_IdentifyNonUNC)
    p_checkExistence_inputs = $(p_checkExistence_inputs)
    p_checkExistence_ouputs = $(p_checkExistence_ouputs)
    PathTypesHTML -> TST_IndividualReport_7
Note: WriterFeatureTypes
Junction_26
    -> AttributeNameSearch [WriterFeatureTypes]
Note: FeatureTypeUserAttributes
Junction_6
    -> AttributeNameSearch [FeatureTypeUserAttributes]
    -> AttributeNameSearch [FeatureTypeUserAttributes_2]
Note: ReaderFeatureTypes
Junction_24
    -> AttributeNameSearch [ReaderFeatureTypes]
Note: transformerfeaturetype
Junction_27
    -> AttributeNameSearch [transformerfeaturetype]
Note: Transformers
Junction_28
    -> AttributeNameSearch [Transformers]
AttributeNameSearch
    FEATURE_TYPE_ID = @Value(feature_type_id)
    TRANSFORMER_ID = @Value(transformer_id)
    USER_ATTRIBUTE_TYPE = @Value(user_attribute_type)
    WORKSPACE_ID = @Value(workspace_id)
    p_attrSearch_Reader = $(p_attrSearch_Reader)
    p_attrSearch_Transformer = $(p_attrSearch_Transformer)
    p_attrSearch_Writer = $(p_attrSearch_Writer)
    p_attrSearch_wildcard = $(p_attrSearch_wildcard)
    AttributeNamesHTML -> TST_IndividualReport_7
Note: Published Parameters
Junction_30
    -> PublishedParameterSearch [PublisherParameters]
PublishedParameterSearch
    CUSTOM_TRANSFORMER_PARENT_NAME = @Value(custom_transformer_parent_name)
    FME_BASENAME = @Value(fme_basename)
    FME_DATASET = @Value(fme_dataset)
    PUBLISHED_PARAMETER_DEFAULT_VALUE = @Value(published_parameter_default_value)
    PUBLISHED_PARAMETER_NAME = @Value(published_parameter_name)
    PUBLISHED_PARAMETER_TYPE = @Value(published_parameter_type)
    WORKSPACE_ID = @Value(workspace_id)
    p_paramsearch_wildcard = $(p_paramsearch_wildcard)
    p_pubparam_defaultvalue = $(p_pubparam_defaultvalue)
    p_pubparam_name = $(p_pubparam_name)
    PublishParameterHTML -> TST_IndividualReport_7
Note: ReaderFeatureTypes
Junction_4
    -> Tester_11
Note: Readers
Junction_3
    -> Tester_12
Note: reader parameters
Junction_13
    -> Tester_10
Note: Transformer Parameters
Junction_21
    -> AttributeKeeper_18
Note: Transformers
Junction_19
    -> AttributeKeeper_17
Note: WriterFeatureTypes
Junction_5
    -> Tester_17
Note: Writers
Junction_11
    -> Tester_19
Note: Writer Params
Junction_12
    -> Tester_18

Bookmark: Read Parent Directory and Identify all FMW/FMX files
Creator
    GEOMTYPE = Geometry Object
    NUM = 1
    CREATED -> FeatureReader [INITIATOR]
Note: FeatureReader [FeatureReader] / Reading: / Reader: / Dataset: $(p_ParentDirectory) / Coordinate System: <not set> / Constraints: / Feature Types to Read: <not set> / Feature Type Separator: SPACE / WHERE Clause: <not set> / Spatial Filter: <No Spatial Filter> / Max Features to Read: <not set> / Schema/Data Features: / Features To Read: Schema and Data Features / Output: / Output Ports: / [x] Single Output Port Regenerate: [ ] / Attribute and Geometry Handling: / Accumulation Mode: Only Use Result / Geometry: Use Result / <Generic> Port: / Attributes to Expose: <not set>
FeatureReader
    ATTR_ACCUM_MODE = Only Use Result
    COMBINE_GEOM = Use Result
    DATASET = $(p_ParentDirectory)
    FORMAT = PATH
    OUTPUT_FEATURES_DISPLAY = Schema and Data Features
    PATH_GLOB_PATTERN = *.fm*
    PATH_NO_EMPTY_PROPERTIES = YES
    PATH_OFFSET_DATETIME = yes
    PATH_PATH_EXPOSE_FORMAT_ATTRS = fme_dataset,char(50)
    PATH_RECURSE_DIRECTORIES = $(p_FolderRecursion)
    PATH_RETRIEVE_FILE_PROPERTIES = NO
    PATH_TYPE = ANY
    PATH_USE_NON_STRING_ATTR = yes
    <OTHER> -> AttributeExposer
AttributeExposer
    ATTR_LIST = path_windows
    -> AttributeCreator_27
AttributeCreator_27
    ATTR_TABLE = SET_TO PathsToIgnore = $(p_ignoreDirectories)
    -> TST_IgnoreDirsHasValue
TST_IgnoreDirsHasValue: Tester
    BOOL_OP = OR
    COMPOSITE_TEST = 1
    TEST_CLAUSE = TEST PathsToIgnore ATTRIBUTE_HAS_A_VALUE ""
    TEST_MODE = TEST
    PASSED -> StringSearcher_3
    FAILED -> StringSearcher_14
Note: wild card search
StringSearcher_4
    CASE = no
    MATCHED_RESULT_ATTR = _first_match
    REGEXP = $(p_wilcardFilePath)
    STRING_TO_SEARCH = @Value(path_windows)
    MATCHED -> FeatureReader_3 [INITIATOR]

Bookmark: Directory Ignore
StringSearcher_3
    CASE = no
    MATCHED_RESULT_ATTR = _first_match
    REGEXP = $(p_ignoreDirectories)
    STRING_TO_SEARCH = @Value(path_windows)
    NOT_MATCHED -> StringSearcher_4
StringSearcher_14
    CASE = no
    MATCHED_RESULT_ATTR = _first_match
    REGEXP = $(p_ignoreDirectories)
    STRING_TO_SEARCH = @Value(path_windows)
    MATCHED -> StringSearcher_4

Bookmark: Search For Inputs/Outputs
Tester_11
    BOOL_OP = OR
    COMPOSITE_TEST = 1
    TEST_CLAUSE = TEST $(p_searchInputs) = YES
    TEST_MODE = TEST
    PASSED -> AttributeKeeper_11
AttributeKeeper_11
    CREATE_BULK_MODE_FEATURES = NO
    KEEP_ATTRS = fme_dataset,reader_feature_type_name,fme_basename,reader_feature_type_enabled,reader_feature_type_qualifier,reader_id,workspace_id
    -> FeatureJoiner_5 [RIGHT]
Tester_12
    BOOL_OP = OR
    COMPOSITE_TEST = 1
    TEST_CLAUSE = TEST $(p_searchInputs) = YES
    TEST_MODE = TEST
    PASSED -> AttributeKeeper_12
Note: IDENTIFY COMPOUND ATTRIBUTES AND SPLIT HERE
AttributeKeeper_12
    CREATE_BULK_MODE_FEATURES = NO
    KEEP_ATTRS = fme_basename,fme_dataset,fme_feature_type,reader_enabled,reader_id,reader_name,reader_type,source_dataset,workspace_id
    -> FeatureJoiner_3 [LEFT]
Tester_10
    BOOL_OP = OR
    COMPOSITE_TEST = 1
    TEST_CLAUSE = TEST $(p_searchInputs) = YES
    TEST_MODE = TEST
    PASSED -> AttributeKeeper_13
AttributeKeeper_13
    CREATE_BULK_MODE_FEATURES = NO
    KEEP_ATTRS = reader_id,workspace_id,reader_parameter_name,reader_parameter_value
    -> Tester_4
Tester_4
    BOOL_OP = OR
    COMPOSITE_TEST = 1 OR 2
    TEST_CLAUSE:
      CASE_INSENSITIVE_TEST @Value(reader_parameter_name) CONTAINS DATASET_
      CASE_INSENSITIVE_TEST @Value(reader_parameter_name) CONTAINS _DATASET
    TEST_MODE = PER_TEST
    PASSED -> ListBuilder
ListBuilder
    GROUP_BY = reader_id workspace_id fme_feature_type
    LIST_ATTRS_TO_INCLUDE = reader_parameter_name reader_parameter_value
    LIST_NAME = _list
    -> AttributeCreator_7
AttributeCreator_7
    ATTR_TABLE:
      SET_TO dataset_format = @Value(_list{0}.reader_parameter_value)
      SET_TO dataset_location = @Value(_list{1}.reader_parameter_value)
    -> FeatureJoiner_3 [RIGHT]
FeatureJoiner_3
    ATTR_CONFLICT_RES = Use Left
    GEOMETRY_HANDLING = Use Left
    JOIN_KEYS = workspace_id workspace_id AUTO reader_id reader_id AUTO
    JOIN_MODE = Inner
    JOINED -> FeatureJoiner_5 [LEFT]
FeatureJoiner_5
    ATTR_CONFLICT_RES = Use Left
    GEOMETRY_HANDLING = Use Left
    JOIN_KEYS = workspace_id workspace_id AUTO reader_id reader_id AUTO
    JOIN_MODE = Inner
    JOINED -> AttributeManager_5
    UNJOINED_LEFT -> AttributeManager_5
    UNJOINED_RIGHT -> AttributeManager_5
AttributeManager_5
    ATTR_TABLE:
      SET_TO reader_feature_type_name = FME_CONDITIONAL:DEFAULT_VALUE'_FME_NO_OP_'BOOL_OP;COMPOSITE;COMPOSITE_TEST;1 OR 2 OR 3 OR 4 OR ( 5 AND 6 );TEST reader_feature_type_name ATTRIBUTE_VALUE_NULL _FME_BLANK_STRING_;TEST reader_feature_type_name ATTRIBUTE_IS_EMPTY _FME_BLANK_STRING_;TEST reader_feature_type_name ATTRIBUTE_IS_MISSING _FME_BLANK_STRING_;TEST @Value(reader_feature_type_name) = @Value(reader_type);TEST @Value(reader_feature_type_name) = CSV;TEST @Value(reader_type) = CSV2'@Value(dataset_location)'BOOL_OP;OR;COMPOSITE_TEST;1;TEST reader_feature_type_qualifier ATTRIBUTE_HAS_A_VALUE _FME_BLANK_STRING_'@Value(reader_feature_type_qualifier).@Value(reader_feature_type_name)'FME_NUM_CONDITIONS3___
      REMOVE _list{}.reader_parameter_name
      REMOVE _list{}.reader_parameter_value
    -> StringReplacer_3
StringReplacer_3
    CASE = NO
    FIND_TEXT = .*[/\\](.*)$
    NO_MATCH = _FME_NO_OP_
    REGEXP = YES
    REPLACE_TEXT = \1
    SRC_ATTRS = reader_feature_type_name
    -> TestFilter_7
TestFilter_7
    DEFAULT_VALUE = <UNFILTERED>
    TEST_LIST = "BOOL_OP,OR,COMPOSITE_TEST,""""""1"""""",TEST_CLAUSE,CASE_INSENSITIVE_TEST @Value(dataset_location) CONTAINS_REGEX ^https?",url,"BOOL_OP,OR,COMPOSITE_TEST,""""""1"""""",TEST_CLAUSE,CASE_SENSITIVE_TEST @Value(dataset_location) CONTAINS_REGEX ^"?"?\\\\",unc,"BOOL_OP,OR,COMPOSITE_TEST,""""""1"""""",TEST_CLAUSE,CASE_SENSITIVE_TEST @Value(dataset_location) CONTAINS_REGEX ^\w\:[\\/]",local disk
    unc -> StringReplacer_4
    local disk -> StringReplacer_4
StringReplacer_4
    CASE = NO
    FIND_TEXT = (.*[/\\])(.*)$
    NO_MATCH = _FME_NO_OP_
    REGEXP = YES
    REPLACE_TEXT = \1
    SRC_ATTRS = fme_dataset
    -> AttributeManager_6
AttributeManager_6
    ATTR_TABLE:
      RENAME_SET_VALUE fme_dataset > Directory
      RENAME_SET_VALUE fme_basename > Workspace Name
      SET_TO Transformer Type = Reader
      RENAME_SET_VALUE reader_name > Transformer Name
      SET_TO Format = @Value(dataset_format) - @Value(reader_type)
      RENAME_SET_VALUE reader_enabled > Enabled?
      RENAME_SET_VALUE reader_feature_type_name > Feature Name
      RENAME_SET_VALUE source_dataset > Feature Location
      RENAME_SET_VALUE reader_id > transformer_id
      REMOVE _list{}.reader_parameter_name
      REMOVE _list{}.reader_parameter_value
      REMOVE reader_feature_type_qualifier
      REMOVE reader_feature_type_enabled
      REMOVE dataset_format
      REMOVE reader_type
      REMOVE fme_feature_type
      REMOVE fme_geometry{}
      REMOVE dataset_location
    -> Junction_22
AttributeKeeper_18
    CREATE_BULK_MODE_FEATURES = NO
    KEEP_ATTRS = custom_transformer_parent_name,transformer_id,transformer_parameter_name,transformer_parameter_value,workspace_id
    -> Tester_14
    -> Tester_16
Tester_14
    BOOL_OP = OR
    COMPOSITE_TEST = 1
    TEST_CLAUSE = TEST $(p_searchInputs) = YES
    TEST_MODE = TEST
    PASSED -> FeatureJoiner_8 [RIGHT]
Tester_16
    BOOL_OP = OR
    COMPOSITE_TEST = 1
    TEST_CLAUSE = TEST $(p_searchOutputs) = YES
    TEST_MODE = TEST
    PASSED -> FeatureJoiner_9 [RIGHT]
AttributeKeeper_17
    CREATE_BULK_MODE_FEATURES = NO
    KEEP_ATTRS = custom_transformer_parent_name,fme_basename,fme_dataset,transformer_enabled,transformer_id,transformer_name,transformer_type,workspace_id
    -> TestFilter_15
TestFilter_15
    DEFAULT_VALUE = <UNFILTERED>
    TEST_LIST = "BOOL_OP,OR,COMPOSITE_TEST,""""""1"""""",TEST_CLAUSE,TEST @Value(transformer_type) = FeatureReader",FeatureReader,"BOOL_OP,OR,COMPOSITE_TEST,""""""1"""""",TEST_CLAUSE,TEST @Value(transformer_type) = FeatureWriter",FeatureWriter
    FeatureReader -> Tester_13
    FeatureWriter -> Tester_15
Tester_13
    BOOL_OP = OR
    COMPOSITE_TEST = 1
    TEST_CLAUSE = TEST $(p_searchInputs) = YES
    TEST_MODE = TEST
    PASSED -> FeatureJoiner_8 [LEFT]
FeatureJoiner_8
    ATTR_CONFLICT_RES = Use Left
    GEOMETRY_HANDLING = Use Left
    JOIN_KEYS = workspace_id workspace_id AUTO transformer_id transformer_id AUTO
    JOIN_MODE = Inner
    JOINED -> Tester_8
Tester_8
    BOOL_OP = OR
    COMPOSITE_TEST = 1 OR 2 OR 3 OR 4
    TEST_CLAUSE:
      TEST @Value(transformer_parameter_name) = FEATURETYPES
      TEST @Value(transformer_parameter_name) = DATASET
      TEST @Value(transformer_parameter_name) = GEODATABASE_SDE_CONNECTION_FILE
      TEST @Value(transformer_parameter_name) = FORMAT
    TEST_MODE = TEST
    PASSED -> Sorter_36
Sorter_36
    SORT_PARM = workspace_id NATURAL ASCENDING transformer_id NATURAL ASCENDING transformer_parameter_name NATURAL ASCENDING
    SORTED -> ListBuilder_3
ListBuilder_3
    GROUP_BY = custom_transformer_parent_name fme_basename fme_dataset fme_feature_type transformer_enabled transformer_id transformer_name transformer_type workspace_id
    LIST_ATTRS_TO_INCLUDE = transformer_parameter_name transformer_parameter_value
    LIST_NAME = _list
    -> ListSearcher
ListSearcher
    ATTR_VALUE = GEODATABASE_SDE_CONNECTION_FILE
    INDEX_ATTR = _list_index
    LIST_ATTR = _list{}.transformer_parameter_name
    MATCHTYPE = FIRST_MATCHED_ENCODED
    FOUND -> AttributeCreator_12
    NOT_FOUND -> AttributeCreator_11
AttributeCreator_12
    ATTR_TABLE:
      SET_TO Features = @Value(_list{1}.transformer_parameter_value)
      SET_TO Format = @Value(_list{2}.transformer_parameter_value)
      SET_TO Dataset = @Value(_list{3}.transformer_parameter_value)
    -> AttributeManager_7
AttributeCreator_11
    ATTR_TABLE:
      SET_TO Dataset = @Value(_list{0}.transformer_parameter_value)
      SET_TO Features = @Value(_list{1}.transformer_parameter_value)
      SET_TO Format = @Value(_list{2}.transformer_parameter_value)
    -> AttributeManager_7
AttributeManager_7
    ATTR_TABLE:
      RENAME_SET_VALUE fme_dataset > Directory = @ReplaceRegularExpression(@Value(Directory),@Value(fme_basename).fm[wx],,caseSensitive=TRUE)
      RENAME_SET_VALUE fme_basename > Workspace Name
      RENAME_SET_VALUE transformer_type > Transformer Type
      RENAME_SET_VALUE transformer_name > Transformer Name = FME_CONDITIONAL:DEFAULT_VALUE'_FME_NO_OP_'BOOL_OP;OR;COMPOSITE_TEST;1;TEST custom_transformer_parent_name ATTRIBUTE_HAS_A_VALUE _FME_BLANK_STRING_'@Value(Transformer Name) (@Value(custom_transformer_parent_name))'FME_NUM_CONDITIONS2___
      RENAME_SET_VALUE transformer_enabled > Enabled?
      RENAME_SET_VALUE Features > Feature Name = FME_CONDITIONAL:DEFAULT_VALUE'_FME_NO_OP_'BOOL_OP;OR;COMPOSITE_TEST;1;TEST Feature Name NOT_ATTRIBUTE_HAS_A_VALUE _FME_BLANK_STRING_'@ReplaceRegularExpression(@Value(Dataset),.*[/\\](.*),\1,caseSensitive=TRUE)'FME_NUM_CONDITIONS2___
      RENAME_SET_VALUE Dataset > Feature Location
      REMOVE _list{}.transformer_parameter_name
      REMOVE _list{}.transformer_parameter_value
      REMOVE _list_index
      REMOVE custom_transformer_parent_name
    -> Junction_22
Junction_22
    -> StringSearcher
StringSearcher
    CASE = no
    MATCHED_RESULT_ATTR = _first_match
    REGEXP = $(p_FeatureWildcard)
    STRING_TO_SEARCH = @Value(Feature Name)
    MATCHED -> HTMLReportGenerator_67
HTMLReportGenerator_67
    CONTENT_LIST = HEADER TABLE
    GROUP_BY = Directory "Workspace Name"
    PAGE_CONFIG = HEADER{{TEXT;-Workspace: @Value(Workspace Name);HEADER;H6;HEADER_ID;;ALIGNMENT;LEFT;COLOR;0,0,0;FME_CONTROLLER_QUERY_FILE;transformers/dependencies/html5/Header.fme;FME_CONTROLLER_CHOICE;Header}}TABLE{{STYLE;DEFAULT;TABLE;Transformer Name|Transformer Name/Transformer Type|Transformer Type/Format|Format/Enabled?|Enabled/Feature Name|Feature Name/Feature Location|Feature Location;FME_CONTROLLER_QUERY_FILE;transformers/dependencies/html5/Table.fme;FME_CONTROLLER_CHOICE;Table}}
    -> HTMLLayouter_41
HTMLLayouter_41
    DIV_STYLE = SOLID
    GROUP_BY = Directory
    LAYOUT = VERTICAL
    -> HTMLReportGenerator_68
HTMLReportGenerator_68
    CONTENT_LIST = HEADER HTML
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> HTMLLayouter_40
HTMLLayouter_40
    DIV_STYLE = NONE
    LAYOUT = VERTICAL
    -> HTMLReportGenerator_69
HTMLReportGenerator_69
    CONTENT_LIST = HEADER HTML
    PAGE_CONFIG = HEADER{{TEXT;Input Features;HEADER;H3;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Input Features
    -> Counter_32
Counter_32
    CNT_ATTR = _count
    SCOPE = Local
    START = 0
    -> Sorter_38
Tester_15
    BOOL_OP = OR
    COMPOSITE_TEST = 1
    TEST_CLAUSE = TEST $(p_searchOutputs) = YES
    TEST_MODE = TEST
    PASSED -> FeatureJoiner_9 [LEFT]
FeatureJoiner_9
    ATTR_CONFLICT_RES = Use Left
    GEOMETRY_HANDLING = Use Left
    JOIN_KEYS = workspace_id workspace_id AUTO transformer_id transformer_id AUTO
    JOIN_MODE = Inner
    JOINED -> Tester_9
Tester_9
    BOOL_OP = OR
    COMPOSITE_TEST = 1 OR 2 OR 3
    TEST_CLAUSE:
      TEST @Value(transformer_parameter_name) = DATASET
      TEST @Value(transformer_parameter_name) = FORMAT
      TEST @Value(transformer_parameter_name) = WRITER_FEATURE_TYPE_PARAMS
    TEST_MODE = TEST
    PASSED -> Sorter_37
Sorter_37
    SORT_PARM = workspace_id NATURAL ASCENDING transformer_id NATURAL ASCENDING transformer_parameter_name NATURAL ASCENDING
    SORTED -> ListBuilder_4
ListBuilder_4
    GROUP_BY = custom_transformer_parent_name fme_basename fme_dataset fme_feature_type transformer_enabled transformer_id transformer_name transformer_type workspace_id
    LIST_ATTRS_TO_INCLUDE = transformer_parameter_name transformer_parameter_value
    LIST_NAME = _list
    -> AttributeCreator_13
AttributeCreator_13
    ATTR_TABLE:
      SET_TO Format = @Value(_list{1}.transformer_parameter_value)
      SET_TO Dataset = @Value(_list{0}.transformer_parameter_value)
      SET_TO Feature Name = @Value(_list{2}.transformer_parameter_value)
    -> AttributeSplitter_3
AttributeSplitter_3
    ATTR_NAME = Feature Name
    DELIMITER = :
    DROP_EMPTY_PARTS = Yes
    LIST_NAME = _featureParamList
    TRIM_OPTION = Both
    -> AttributeCreator_14
AttributeCreator_14
    ATTR_TABLE = SET_TO Feature Name = @Value(_featureParamList{0})
    -> AttributeManager_8
AttributeManager_8
    ATTR_TABLE:
      RENAME_SET_VALUE fme_dataset > Directory = @ReplaceRegularExpression(@Value(Directory),@Value(fme_basename).fm[wx],,caseSensitive=TRUE)
      RENAME_SET_VALUE fme_basename > Workspace Name
      RENAME_SET_VALUE transformer_type > Transformer Type
      RENAME_SET_VALUE transformer_name > Transformer Name = FME_CONDITIONAL:DEFAULT_VALUE'_FME_NO_OP_'BOOL_OP;OR;COMPOSITE_TEST;1;TEST custom_transformer_parent_name ATTRIBUTE_HAS_A_VALUE _FME_BLANK_STRING_'@Value(Transformer Name) (@Value(custom_transformer_parent_name))'FME_NUM_CONDITIONS2___
      RENAME_SET_VALUE transformer_enabled > Enabled?
      RENAME_SET_VALUE Dataset > Feature Location
      REMOVE _list{}.transformer_parameter_name
      REMOVE _list{}.transformer_parameter_value
      REMOVE _list_index
      REMOVE custom_transformer_parent_name
      REMOVE _featureParamList{}
    -> Junction_14
Tester_17
    BOOL_OP = OR
    COMPOSITE_TEST = 1
    TEST_CLAUSE = TEST $(p_searchOutputs) = YES
    TEST_MODE = TEST
    PASSED -> AttributeKeeper_14
AttributeKeeper_14
    CREATE_BULK_MODE_FEATURES = NO
    KEEP_ATTRS = fme_dataset,fme_basename,workspace_id,writer_feature_type_enabled,writer_feature_type_name,writer_feature_type_qualifier,writer_id
    -> FeatureJoiner_7 [RIGHT]
Tester_19
    BOOL_OP = OR
    COMPOSITE_TEST = 1
    TEST_CLAUSE = TEST $(p_searchOutputs) = YES
    TEST_MODE = TEST
    PASSED -> AttributeKeeper_15
AttributeKeeper_15
    CREATE_BULK_MODE_FEATURES = NO
    KEEP_ATTRS = fme_basename,fme_dataset,workspace_id,destination_dataset,writer_enabled,writer_id,writer_name,writer_type
    -> FeatureJoiner_6 [LEFT]
Tester_18
    BOOL_OP = OR
    COMPOSITE_TEST = 1
    TEST_CLAUSE = TEST $(p_searchOutputs) = YES
    TEST_MODE = TEST
    PASSED -> AttributeKeeper_16
AttributeKeeper_16
    CREATE_BULK_MODE_FEATURES = NO
    KEEP_ATTRS = fme_geometry{0},workspace_id,writer_id,writer_parameter_name,writer_parameter_value
    -> Tester_7
Tester_7
    BOOL_OP = OR
    COMPOSITE_TEST = 1 OR 2
    TEST_CLAUSE:
      CASE_INSENSITIVE_TEST @Value(writer_parameter_name) CONTAINS DATASET_
      CASE_INSENSITIVE_TEST @Value(writer_parameter_name) CONTAINS _DATASET
    TEST_MODE = CASE_INSENSITIVE_TEST
    PASSED -> ListBuilder_2
ListBuilder_2
    GROUP_BY = workspace_id fme_feature_type writer_id
    LIST_ATTRS_TO_INCLUDE = writer_parameter_name writer_parameter_value
    LIST_NAME = _list
    -> AttributeCreator_10
AttributeCreator_10
    ATTR_TABLE:
      SET_TO dataset_format = @Value(_list{0}.writer_parameter_value)
      SET_TO dataset_location = @Value(_list{1}.writer_parameter_value)
    -> FeatureJoiner_6 [RIGHT]
FeatureJoiner_6
    ATTR_CONFLICT_RES = Use Left
    GEOMETRY_HANDLING = Use Left
    JOIN_KEYS = workspace_id workspace_id AUTO writer_id writer_id AUTO
    JOIN_MODE = Inner
    JOINED -> FeatureJoiner_7 [LEFT]
FeatureJoiner_7
    ATTR_CONFLICT_RES = Use Left
    GEOMETRY_HANDLING = Use Left
    JOIN_KEYS = workspace_id workspace_id AUTO writer_id writer_id AUTO
    JOIN_MODE = Inner
    JOINED -> AttributeManager_9
    UNJOINED_LEFT -> AttributeManager_9
AttributeManager_9
    ATTR_TABLE = SET_TO writer_feature_type_name = FME_CONDITIONAL:DEFAULT_VALUE'_FME_NO_OP_'BOOL_OP;COMPOSITE;COMPOSITE_TEST;1 OR 2 OR 3 OR 4 OR ( 5 AND 6 );TEST writer_feature_type_name ATTRIBUTE_VALUE_NULL _FME_BLANK_STRING_;TEST writer_feature_type_name ATTRIBUTE_IS_EMPTY _FME_BLANK_STRING_;TEST writer_feature_type_name ATTRIBUTE_IS_MISSING _FME_BLANK_STRING_;TEST @Value(writer_feature_type_name) = @Value(writer_type);TEST @Value(writer_feature_type_qualifier) = CSV;TEST @Value(writer_feature_type_name) = CSV2'@Value(destination_dataset)'BOOL_OP;OR;COMPOSITE_TEST;1;TEST writer_feature_type_qualifier ATTRIBUTE_HAS_A_VALUE _FME_BLANK_STRING_'@Value(writer_feature_type_qualifier).@Value(writer_feature_type_name)'FME_NUM_CONDITIONS3___
    -> StringReplacer_5
StringReplacer_5
    CASE = NO
    FIND_TEXT = .*[/\\](.*)$
    NO_MATCH = _FME_NO_OP_
    REGEXP = YES
    REPLACE_TEXT = \1
    SRC_ATTRS = writer_feature_type_name
    -> TestFilter_14
TestFilter_14
    DEFAULT_VALUE = <UNFILTERED>
    TEST_LIST = "BOOL_OP,OR,COMPOSITE_TEST,""""""1"""""",TEST_CLAUSE,CASE_SENSITIVE_TEST @Value(destination_dataset) CONTAINS_REGEX ^"?"?\\\\",unc,"BOOL_OP,OR,COMPOSITE_TEST,""""""1"""""",TEST_CLAUSE,CASE_SENSITIVE_TEST @Value(destination_dataset) CONTAINS_REGEX ^\w\:[\\/]",local disk
    unc -> StringReplacer_6
    local disk -> StringReplacer_6
    <UNFILTERED> -> AttributeManager_10
StringReplacer_6
    CASE = NO
    FIND_TEXT = (.*[/\\])(.*)$
    NO_MATCH = _FME_NO_OP_
    REGEXP = YES
    REPLACE_TEXT = \1
    SRC_ATTRS = destination_dataset
    -> AttributeManager_10
AttributeManager_10
    ATTR_TABLE:
      RENAME_SET_VALUE fme_dataset > Directory
      RENAME_SET_VALUE fme_basename > Workspace Name
      RENAME_SET_VALUE writer_name > Transformer Name
      SET_TO Transformer Type = Writer
      SET_TO Format = @Value(dataset_format) - @Value(writer_type)
      RENAME_SET_VALUE writer_enabled > Enabled?
      RENAME_SET_VALUE writer_feature_type_name > Feature Name
      RENAME_SET_VALUE destination_dataset > Feature Location
      RENAME_SET_VALUE writer_id > transformer_id
      REMOVE writer_feature_type_qualifier
      REMOVE writer_feature_type_enabled
      REMOVE writer_type
      REMOVE fme_feature_type
      REMOVE dataset_format
      REMOVE dataset_location
      REMOVE _list{}.writer_parameter_name
      REMOVE _list{}.writer_parameter_value
      REMOVE fme_geometry{}
    -> Junction_14
Junction_14
    -> StringSearcher_2
StringSearcher_2
    CASE = no
    MATCHED_RESULT_ATTR = _first_match
    REGEXP = $(p_FeatureWildcard)
    STRING_TO_SEARCH = @Value(Feature Name)
    MATCHED -> HTMLReportGenerator_64
HTMLReportGenerator_64
    CONTENT_LIST = HEADER TABLE
    GROUP_BY = Directory "Workspace Name"
    PAGE_CONFIG = HEADER{{TEXT;-Workspace: @Value(Workspace Name);HEADER;H6;HEADER_ID;;ALIGNMENT;LEFT;COLOR;0,0,0;FME_CONTROLLER_QUERY_FILE;transformers/dependencies/html5/Header.fme;FME_CONTROLLER_CHOICE;Header}}TABLE{{STYLE;DEFAULT;TABLE;Transformer Name|Transformer Name/Transformer Type|Transformer Type/Format|Format/Enabled?|Enabled/Feature Name|Feature Name/Feature Location|Feature Location;FME_CONTROLLER_QUERY_FILE;transformers/dependencies/html5/Table.fme;FME_CONTROLLER_CHOICE;Table}}
    -> HTMLLayouter_39
HTMLLayouter_39
    DIV_STYLE = SOLID
    GROUP_BY = Directory
    LAYOUT = VERTICAL
    -> HTMLReportGenerator_65
HTMLReportGenerator_65
    CONTENT_LIST = HEADER HTML
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> HTMLLayouter_38
HTMLLayouter_38
    DIV_STYLE = NONE
    LAYOUT = VERTICAL
    -> HTMLReportGenerator_66
HTMLReportGenerator_66
    CONTENT_LIST = HEADER HTML
    PAGE_CONFIG = HEADER{{TEXT;Output Features;HEADER;H3;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Output Features
    -> Counter_33
Counter_33
    CNT_ATTR = _count
    SCOPE = Local
    START = 1
    -> Sorter_38
Sorter_38
    SORT_PARM = _count NATURAL ASCENDING
    SORTED -> HTMLLayouter_42
HTMLLayouter_42
    DIV_STYLE = NONE
    LAYOUT = VERTICAL
    -> HTMLReportGenerator_70
HTMLReportGenerator_70
    CONTENT_LIST = HEADER HTML
    PAGE_CONFIG = HEADER{{TEXT;Input/Output Feature Reporting;HEADER;H2;HEADER_ID;;ALIGNMENT;CENTER;COLOR;255,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = I/O Feature Types
    -> StringReplacer_10
StringReplacer_10
    CASE = NO
    FIND_TEXT = $(p_FeatureWildcard)
    NO_MATCH = _FME_NO_OP_
    REGEXP = NO
    REPLACE_TEXT = <b>$(p_FeatureWildcard)</b>
    SRC_ATTRS = html_content
    -> AttributeCreator_24
AttributeCreator_24
    ATTR_TABLE = SET_TO ReportName = InputOutputFeatureTypes.html
    -> TST_IndividualReport_7

Bookmark: Generate Report(s)
TST_IndividualReport_7: Tester
    BOOL_OP = OR
    COMPOSITE_TEST = 1
    TEST_CLAUSE = TEST $(p_IndividualReports) = YES
    TEST_MODE = TEST
    PASSED -> FeatureWriter_8 [HTML]
    FAILED -> Sorter
Sorter
    SORT_PARM = ReportName NATURAL ASCENDING
    SORTED -> HTMLLayouter_52
HTMLLayouter_52
    DIV_STYLE = SOLID
    LAYOUT = VERTICAL
    TITLE = Bulk Workspace Report
    -> AttributeCreator_26
AttributeCreator_26
    ATTR_TABLE = SET_TO ReportName = BulkWorkspaceExaminerReport.html
    -> FeatureWriter_8 [HTML]
FeatureWriter_8
    DATASET = $(p_ReportLocation)/@Value(ReportName)
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written

FME custom transformer IdentifyUpgradeableTransformers

Parameters:
- CURRENT_TRANSFORMER_VERSION =
- CUSTOM_TRANSFORMER_PARENT_NAME =
- FME_BASENAME =
- FME_DATASET =
- MAX_TRANSFORMER_VERSION =
- p_Transformers =
- p_upgradeable =

Transformers (input)
    -> TST:Upgradeable_2
UpgradeableTransformersHTML (output)

Bookmark: Identify Upgradeable Xformers
Note: TST:IdentifyUpgrabeable
TST:Upgradeable_2: Tester
    BOOL_OP = OR
    COMPOSITE_TEST = 1
    TEST_CLAUSE = TEST $(p_upgradeable) = YES
    TEST_MODE = TEST
    PASSED -> Tester_6
Note: Current Version < Max Version
Tester_6
    BOOL_OP = OR
    COMPOSITE_TEST = 1
    TEST_CLAUSE = TEST @Value(current_transformer_version) < @Value(max_transformer_version)
    TEST_MODE = TEST
    PASSED -> AttributeManager_15
Note: Condtionally identify if transformer is in main workspace of custom transformer
AttributeManager_15
    ATTR_TABLE:
      SET_TO Directory = @ReplaceRegularExpression(@Value(fme_dataset),"@Value(fme_basename).fm[wx]","",caseSensitive=TRUE)
      SET_TO Workspace = FME_CONDITIONAL:DEFAULT_VALUE'@Value(fme_basename)'BOOL_OP;OR;COMPOSITE_TEST;1;TEST custom_transformer_parent_name ATTRIBUTE_HAS_A_VALUE _FME_BLANK_STRING_'@Value(fme_basename) (@Value(custom_transformer_parent_name))'FME_NUM_CONDITIONS2___
      SET_TO Location = FME_CONDITIONAL:DEFAULT_VALUE'Main Workspace'BOOL_OP;OR;COMPOSITE_TEST;1;TEST custom_transformer_parent_name ATTRIBUTE_HAS_A_VALUE _FME_BLANK_STRING_'Custom Transformer: @Value(custom_transformer_parent_name)'FME_NUM_CONDITIONS2___
    -> StatisticsCalculator_2
StatisticsCalculator_2
    CALCULATION_MODE = NUMERIC
    FEAT_STATS = transformer_name,NUMERIC_MODE,,,COUNT,,,,,,,,,
    GROUP_BY = Directory fme_basename Workspace Location
    SUMMARY -> Sorter_42
Sorter_42
    SORT_PARM = Directory ALPHA ASCENDING Workspace ALPHA ASCENDING Location ALPHA ASCENDING transformer_name.total_count NUMERIC DESCENDING
    SORTED -> HTMLReportGenerator_71
Note: Generate Report by Workspace/Directory
HTMLReportGenerator_71
    CONTENT_LIST = HEADER TABLE
    GROUP_BY = Directory fme_basename
    PAGE_CONFIG = HEADER{{TEXT;- Workspace: @Value(fme_basename);HEADER;H5;HEADER_ID;;ALIGNMENT;LEFT;COLOR;0,0,0;FME_CONTROLLER_QUERY_FILE;transformers/dependencies/html5/Header.fme;FME_CONTROLLER_CHOICE;Header}}TABLE{{STYLE;DEFAULT;TABLE;Location|Location/transformer_name.total_count|# Upgradeable;FME_CONTROLLER_QUERY_FILE;transformers/dependencies/html5/Table.fme;FME_CONTROLLER_CHOICE;Table}}
    -> HTMLLayouter_43
Note: Combine worksdpace reports into one
HTMLLayouter_43
    DIV_STYLE = NONE
    GROUP_BY = Directory
    LAYOUT = VERTICAL
    -> HTMLReportGenerator_75
Note: Create Directory Reports
HTMLReportGenerator_75
    CONTENT_LIST = HEADER HTML
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> HTMLLayouter_48
Note: Merge Directory Reports
HTMLLayouter_48
    DIV_STYLE = VERTICAL
    LAYOUT = VERTICAL
    -> HTMLReportGenerator_80
Note: Generate Final Report
HTMLReportGenerator_80
    CONTENT_LIST = HEADER HTML
    PAGE_CONFIG = HEADER{{TEXT;UPGRADEABLE TRANSFORMERS;HEADER;H2;HEADER_ID;;ALIGNMENT;CENTER;COLOR;255,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Upgradeable Transformers
    -> AttributeCreator_22
AttributeCreator_22
    ATTR_TABLE = SET_TO ReportName = UpgradeableTransformers.html
    -> UpgradeableTransformersHTML (output)

FME custom transformer PublishedParameterSearch

Parameters:
- CUSTOM_TRANSFORMER_PARENT_NAME =
- FME_BASENAME =
- FME_DATASET =
- PUBLISHED_PARAMETER_DEFAULT_VALUE =
- PUBLISHED_PARAMETER_NAME =
- PUBLISHED_PARAMETER_TYPE =
- WORKSPACE_ID =
- p_paramsearch_wildcard =
- p_pubparamSearch =
- p_pubparam_defaultvalue =
- p_pubparam_name =
- p_wildcardSearches =

PublisherParameters (input)
    -> TestFilter_16
PublishParameterHTML (output)

Bookmark: Published parameter Search
TestFilter_16
    DEFAULT_VALUE = <UNFILTERED>
    TEST_LIST:
      "BOOL_OP,AND,COMPOSITE_TEST,""""""1 AND 2"""""",TEST_CLAUSE,TEST $(p_pubparam_name) = YES
      TEST $(p_pubparam_defaultvalue) = YES",Name / Value,"BOOL_OP,AND,COMPOSITE_TEST,""""""1 AND 2"""""",TEST_CLAUSE,TEST $(p_pubparam_name) = YES
      TEST $(p_pubparam_defaultvalue) = NO",Name,"BOOL_OP,AND,COMPOSITE_TEST,""""""1 AND 2"""""",TEST_CLAUSE,TEST $(p_pubparam_name) = NO
      TEST $(p_pubparam_defaultvalue) = YES",Value
    Name / Value -> StringSearcher_9
    Name / Value -> StringSearcher_12
    Name -> StringSearcher_10
    Value -> StringSearcher_11
StringSearcher_10
    CASE = no
    REGEXP = $(p_paramsearch_wildcard)
    STRING_TO_SEARCH = @Value(published_parameter_name)
    MATCHED -> DuplicateFilter
StringSearcher_9
    CASE = no
    REGEXP = $(p_paramsearch_wildcard)
    STRING_TO_SEARCH = @Value(published_parameter_name)
    MATCHED -> DuplicateFilter
StringSearcher_12
    CASE = no
    REGEXP = $(p_paramsearch_wildcard)
    STRING_TO_SEARCH = @Value(published_parameter_default_value)
    MATCHED -> DuplicateFilter
StringSearcher_11
    CASE = no
    REGEXP = $(p_paramsearch_wildcard)
    STRING_TO_SEARCH = @Value(published_parameter_default_value)
    MATCHED -> DuplicateFilter
DuplicateFilter
    INPUT_ORDERED_CHOICE = No
    KEYATTR = custom_transformer_parent_name fme_basename fme_dataset fme_feature_type published_parameter_default_value published_parameter_name published_parameter_type workspace_id
    UNIQUE -> AttributeManager_20
AttributeManager_20
    ATTR_TABLE:
      RENAME_SET_VALUE fme_dataset > Directory = @ReplaceRegularExpression(@Value(Directory),@Value(fme_basename).fm[wx],,caseSensitive=TRUE)
      RENAME_SET_VALUE fme_basename > Workspace
      RENAME_SET_VALUE published_parameter_name > Parameter Name = FME_CONDITIONAL:DEFAULT_VALUE'_FME_NO_OP_'BOOL_OP;OR;COMPOSITE_TEST;1;TEST custom_transformer_parent_name ATTRIBUTE_HAS_A_VALUE _FME_BLANK_STRING_'@Value(Parameter Name) (Inside CT: @Value(custom_transformer_parent_name))'FME_NUM_CONDITIONS2___
      RENAME_SET_VALUE published_parameter_default_value > Parameter Default Value
      REMOVE fme_geometry{}
      REMOVE workspace_id
      REMOVE published_parameter_type
      REMOVE custom_transformer_parent_name
      REMOVE fme_feature_type
    -> HTMLReportGenerator_82
HTMLReportGenerator_82
    CONTENT_LIST = HEADER TABLE
    GROUP_BY = Directory Workspace
    PAGE_CONFIG = HEADER{{TEXT;Workspace: @Value(Workspace);HEADER;H6;HEADER_ID;;ALIGNMENT;LEFT;COLOR;0,0,255;FME_CONTROLLER_QUERY_FILE;transformers/dependencies/html5/Header.fme;FME_CONTROLLER_CHOICE;Header}}TABLE{{STYLE;BORDERED;TABLE;Parameter Name|Parameter Name/Parameter Default Value|Parameter Default Value;FME_CONTROLLER_QUERY_FILE;transformers/dependencies/html5/Table.fme;FME_CONTROLLER_CHOICE;Table}}
    TITLE = Parameter Search
    -> HTMLLayouter_50
HTMLLayouter_50
    DIV_STYLE = SOLID
    GROUP_BY = Directory
    LAYOUT = VERTICAL
    -> HTMLReportGenerator_83
HTMLReportGenerator_83
    CONTENT_LIST = HEADER HTML
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> HTMLLayouter_51
HTMLLayouter_51
    DIV_STYLE = NONE
    LAYOUT = VERTICAL
    -> StringReplacer_9
StringReplacer_9
    CASE = NO
    FIND_TEXT = $(p_paramsearch_wildcard)
    NO_MATCH = _FME_NO_OP_
    REGEXP = NO
    REPLACE_TEXT = <b><i>$(p_paramsearch_wildcard)</b></i>
    SRC_ATTRS = html_content
    -> HTMLReportGenerator_84
HTMLReportGenerator_84
    CONTENT_LIST = HEADER HTML
    PAGE_CONFIG = HEADER{{TEXT;Parameter Search;HEADER;H2;HEADER_ID;;ALIGNMENT;CENTER;COLOR;255,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Attribute Search
    -> AttributeCreator
AttributeCreator
    ATTR_TABLE = SET_TO ReportName = PublishedParameterSearch.html
    -> PublishParameterHTML (output)

FME custom transformer WorkspaceOverviews

Parameters:
- FME_BASENAME =
- FME_DATASET =
- p_GenerateDescription =
- p_HistoryDescription =

WorkspaceProperties (input)
    -> TST:Description
WorkspaceOverviewsHTML (output)

Bookmark: Workspace Overview
TST:Description: Tester
    BOOL_OP = OR
    COMPOSITE_TEST = 1
    TEST_CLAUSE = TEST $(p_GenerateDescription) = YES
    TEST_MODE = TEST
    PASSED -> AttributeCreator_2
AttributeCreator_2
    ATTR_TABLE = SET_TO Directory = @ReplaceRegularExpression(@Value(fme_dataset),"@Value(fme_basename).fm[wx]","",caseSensitive=TRUE)
    -> AttributeKeeper_6
AttributeKeeper_6
    CREATE_BULK_MODE_FEATURES = NO
    KEEP_ATTRS = fme_basename,workspace_description,Directory
    -> TST:Description_HasValue
TST:Description_HasValue: Tester
    BOOL_OP = OR
    COMPOSITE_TEST = 1
    TEST_CLAUSE = TEST workspace_description ATTRIBUTE_HAS_A_VALUE ""
    TEST_MODE = TEST
    PASSED -> HTMLReportGenerator_4
    FAILED -> Sorter_2
HTMLReportGenerator_4
    CONTENT_LIST = HEADER TABLE
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}TABLE{{STYLE;BORDERED;TABLE;fme_basename|Workspace/workspace_description|Overview;FME_CONTROLLER_QUERY_FILE;transformers/dependencies/html5/Table.fme;FME_CONTROLLER_CHOICE;Table}}
    TITLE = Workspace Descriptions
    -> HTMLLayouter_3
HTMLLayouter_3
    DIV_STYLE = SOLID
    LAYOUT = VERTICAL
    TITLE = Workspace Overviews
    -> HTMLReportGenerator_5
HTMLReportGenerator_5
    CONTENT_LIST = HEADER HTML
    PAGE_CONFIG = HEADER{{TEXT;WORKSPACE DESCRIPTIONS;HEADER;H2;HEADER_ID;;ALIGNMENT;LEFT;COLOR;0,170,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Workspace overviews
    -> AttributeCreator_6
AttributeCreator_6
    ATTR_TABLE = SET_TO htmlSequence = 3
    -> Sorter_4
Sorter_2
    SORT_PARM = Directory NATURAL ASCENDING fme_basename NATURAL ASCENDING
    SORTED -> HTMLReportGenerator_2
HTMLReportGenerator_2
    CONTENT_LIST = HEADER TABLE
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}TABLE{{STYLE;BORDERED;TABLE;fme_basename|Workspace/Directory|Folder;FME_CONTROLLER_QUERY_FILE;transformers/dependencies/html5/Table.fme;FME_CONTROLLER_CHOICE;Table}}
    TITLE = MISSING DESCRIPTIONS
    -> HTMLLayouter_2
HTMLLayouter_2
    DIV_STYLE = SOLID
    LAYOUT = VERTICAL
    TITLE = MISSING Workspace Overviews
    -> HTMLReportGenerator_6
HTMLReportGenerator_6
    CONTENT_LIST = HEADER HTML
    PAGE_CONFIG = HEADER{{TEXT;MISSING WORKSPACE DESCRIPTIONS;HEADER;H2;HEADER_ID;;ALIGNMENT;LEFT;COLOR;255,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Workspace overviews
    -> AttributeCreator_5
AttributeCreator_5
    ATTR_TABLE = SET_TO htmlSequence = 1
    -> Sorter_4
Sorter_4
    SORT_PARM = htmlSequence NATURAL ASCENDING
    SORTED -> HTMLLayouter_4
HTMLLayouter_4
    DIV_STYLE = NONE
    LAYOUT = VERTICAL
    -> HTMLReportGenerator_51
HTMLReportGenerator_51
    CONTENT_LIST = HEADER HTML
    PAGE_CONFIG = HEADER{{TEXT;WORKSPACE OVERVIEWS;HEADER;H1;HEADER_ID;;ALIGNMENT;CENTER;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Workspace Overview
    -> AttributeCreator_21
AttributeCreator_21
    ATTR_TABLE = SET_TO ReportName = WorkspaceDescriptionReport.html
    -> WorkspaceOverviewsHTML (output)

FME custom transformer GenerateDirectoryStatistics

Parameters:
- TRANSFORMER_TYPE =
- p_GenerateStatistics =
- p_ParentDirectory =
- p_Reporting =
- p_StatsGenericizeXFormerNames =
- p_WorkspaceStatistics =

ReaderHistogram (input)
    -> Junction_17
TransformerHistogram (input)
    -> TestFilter_13
WriterHistogram (input)
    -> Junction_15
DirectoryStatisticsHTML (output)

Bookmark: Directory Statistics
TestFilter_13
    DEFAULT_VALUE = TRANSFORMERS
    TEST_LIST = "BOOL_OP,OR,COMPOSITE_TEST,""""""1"""""",TEST_CLAUSE,TEST @Value(transformer_type) = FeatureReader",FeatureReader,"BOOL_OP,OR,COMPOSITE_TEST,""""""1"""""",TEST_CLAUSE,TEST @Value(transformer_type) = FeatureWriter",FeatureWriter
    FeatureReader -> AttributeRenamer_6
    FeatureWriter -> AttributeRenamer_7
    TRANSFORMERS -> Junction_23
AttributeRenamer_6
    ATTR_TABLE:
      RENAME_SET_DEFAULT transformer_type > reader_type
      RENAME_SET_DEFAULT transformer_count > reader_count
    MISSING_INPUT_ATTRS = REMOVE
    -> Junction_17
Junction_17
    -> AttributeCreator_17
AttributeCreator_17
    ATTR_TABLE = SET_TO xFormerTypeGeneric = Reader
    -> AttributeRenamer_5
AttributeRenamer_5
    ATTR_TABLE:
      RENAME_SET_DEFAULT reader_count > transformer_count
      RENAME_SET_DEFAULT reader_type > transformer_type
    MISSING_INPUT_ATTRS = REMOVE
    -> Tester_20
Junction_23
    -> AttributeCreator_16
AttributeCreator_16
    ATTR_TABLE = SET_TO xFormerTypeGeneric = Transformer
    -> Tester_20
AttributeRenamer_7
    ATTR_TABLE:
      RENAME_SET_DEFAULT transformer_type > writer_type
      RENAME_SET_DEFAULT transformer_count > writer_count
    MISSING_INPUT_ATTRS = REMOVE
    -> Junction_15
Junction_15
    -> AttributeCreator_15
AttributeCreator_15
    ATTR_TABLE = SET_TO xFormerTypeGeneric = Writer
    -> AttributeRenamer_4
AttributeRenamer_4
    ATTR_TABLE:
      RENAME_SET_DEFAULT writer_count > transformer_count
      RENAME_SET_DEFAULT writer_type > transformer_type
    MISSING_INPUT_ATTRS = REMOVE
    -> Tester_20
Tester_20
    BOOL_OP = OR
    COMPOSITE_TEST = 1
    TEST_CLAUSE = TEST $(p_StatsGenericizeXFormerNames) = YES
    TEST_MODE = TEST
    PASSED -> AttributeManager_11
    FAILED -> StringSearcher_7
    FAILED -> StringSearcher_6
    FAILED -> StringSearcher_5
AttributeManager_11
    ATTR_TABLE = RENAME_SET_VALUE xFormerTypeGeneric > transformer_type
    -> StringSearcher_7
    -> StringSearcher_6
    -> StringSearcher_5
StringSearcher_5
    CASE = no
    MATCHED_RESULT_ATTR = _first_match
    REGEXP = Yes - Parent Folder Only
    STRING_TO_SEARCH = $(p_GenerateStatistics)
    MATCHED -> Stats-Generic
StringSearcher_6
    CASE = no
    MATCHED_RESULT_ATTR = _first_match
    REGEXP = Yes - By Directory
    STRING_TO_SEARCH = $(p_GenerateStatistics)
    MATCHED -> StringReplacer_7
StringReplacer_7
    CASE = no
    FIND_TEXT = ^(.*[/\\])(.*)$
    NO_MATCH = _FME_NO_OP_
    REGEXP = YES
    REPLACE_TEXT = \1
    SRC_ATTRS = fme_dataset
    -> Stats-Directory_2
StringSearcher_7
    CASE = no
    MATCHED_RESULT_ATTR = _first_match
    REGEXP = Yes - By Directory / Workspace
    STRING_TO_SEARCH = $(p_GenerateStatistics)
    MATCHED -> StringReplacer_8
StringReplacer_8
    CASE = no
    FIND_TEXT = ^(.*[/\\])(.*)$
    NO_MATCH = _FME_NO_OP_
    REGEXP = YES
    REPLACE_TEXT = \1
    SRC_ATTRS = fme_dataset
    -> Stats-Workspace
Stats-Workspace: StatisticsCalculator
    CALCULATION_MODE = NUMERIC
    FEAT_STATS = transformer_count,NUMERIC_MODE,,,,SUM,,,,,,,,
    GROUP_BY = fme_dataset fme_basename transformer_type
    SUMMARY -> AttributeRounder_3
    COMPLETE -> Stats-Directory_4
Stats-Directory_4: StatisticsCalculator
    CALCULATION_MODE = NUMERIC
    FEAT_STATS = transformer_count,NUMERIC_MODE,,,,SUM,,,,,,,,
    GROUP_BY = fme_dataset fme_basename
    SUMMARY -> AttributeManager_14
AttributeManager_14
    ATTR_TABLE = SET_TO transformer_type = Total
    -> AttributeRounder_3
AttributeRounder_3
    PLACES = 0
    ROUND_TYPE = Nearest
    SRC_ATTRS = transformer_count.sum
    -> Sorter_40
Sorter_40
    SORT_PARM = transformer_count.sum NUMERIC DESCENDING
    SORTED -> HTMLReportGenerator_72
HTMLReportGenerator_72
    CONTENT_LIST = HEADER TABLE
    GROUP_BY = fme_dataset fme_basename
    PAGE_CONFIG = HEADER{{TEXT;- Workspace: @Value(fme_basename);HEADER;H6;HEADER_ID;;ALIGNMENT;LEFT;COLOR;0,0,0;FME_CONTROLLER_QUERY_FILE;transformers/dependencies/html5/Header.fme;FME_CONTROLLER_CHOICE;Header}}TABLE{{STYLE;DEFAULT;TABLE;transformer_type|Transformer/transformer_count.sum|Count;FME_CONTROLLER_QUERY_FILE;transformers/dependencies/html5/Table.fme;FME_CONTROLLER_CHOICE;Table}}
    -> HTMLLayouter_44
HTMLLayouter_44
    DIV_STYLE = SOLID
    GROUP_BY = fme_dataset
    LAYOUT = VERTICAL
    -> HTMLReportGenerator_74
HTMLReportGenerator_74
    CONTENT_LIST = HEADER HTML
    GROUP_BY = fme_dataset
    PAGE_CONFIG = HEADER{{TEXT;Parent Directory: @Value(fme_dataset);HEADER;H5;HEADER_ID;;ALIGNMENT;LEFT;COLOR;0,0,255;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> HTMLLayouter_45
HTMLLayouter_45
    DIV_STYLE = NONE
    LAYOUT = VERTICAL
    -> HTMLReportGenerator_73
HTMLReportGenerator_73
    CONTENT_LIST = HEADER HTML
    PAGE_CONFIG = HEADER{{TEXT;Transformer Statistics by Directory / Workspace;HEADER;H3;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_36
Counter_36
    CNT_ATTR = _count
    SCOPE = Local
    START = 2
    -> Sorter_41
Sorter_41
    SORT_PARM = _count NATURAL ASCENDING
    SORTED -> HTMLLayouter_46
HTMLLayouter_46
    DIV_STYLE = SOLID
    LAYOUT = VERTICAL
    -> HTMLReportGenerator_77
HTMLReportGenerator_77
    CONTENT_LIST = HEADER HTML
    PAGE_CONFIG = HEADER{{TEXT;Workspace Statistics;HEADER;H2;HEADER_ID;;ALIGNMENT;CENTER;COLOR;255,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Workspace Statistics
    -> AttributeCreator_25
AttributeCreator_25
    ATTR_TABLE = SET_TO ReportName = DirectoryWorkspaceStatistics.html
    -> DirectoryStatisticsHTML (output)

Bookmark: Generic Statistics
Stats-Generic: StatisticsCalculator
    CALCULATION_MODE = NUMERIC
    FEAT_STATS = transformer_count,NUMERIC_MODE,,,,SUM,,,,,,,,
    GROUP_BY = transformer_type
    SUMMARY -> AttributeRounder
    COMPLETE -> Stats-Generic_2
Stats-Generic_2: StatisticsCalculator
    CALCULATION_MODE = NUMERIC
    FEAT_STATS = transformer_count,NUMERIC_MODE,,,,SUM,,,,,,,,
    SUMMARY -> AttributeManager_13
AttributeManager_13
    ATTR_TABLE = SET_TO transformer_type = Total
    -> AttributeRounder
AttributeRounder
    PLACES = 0
    ROUND_TYPE = Nearest
    SRC_ATTRS = transformer_count.sum
    -> Sorter_39
Sorter_39
    SORT_PARM = transformer_count.sum NUMERIC DESCENDING
    SORTED -> HTMLReportGenerator_63
HTMLReportGenerator_63
    CONTENT_LIST = HEADER TABLE
    PAGE_CONFIG = HEADER{{TEXT;Parent Directory: $(p_ParentDirectory);HEADER;H5;HEADER_ID;;ALIGNMENT;LEFT;COLOR;0,0,255;FME_CONTROLLER_QUERY_FILE;transformers/dependencies/html5/Header.fme;FME_CONTROLLER_CHOICE;Header}}TABLE{{STYLE;DEFAULT;TABLE;transformer_type|Transformer/transformer_count.sum|Count;FME_CONTROLLER_QUERY_FILE;transformers/dependencies/html5/Table.fme;FME_CONTROLLER_CHOICE;Table}}
    -> HTMLReportGenerator_76
HTMLReportGenerator_76
    CONTENT_LIST = HEADER HTML
    PAGE_CONFIG = HEADER{{TEXT;Transformer Statistics - Overall;HEADER;H3;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_34
Counter_34
    CNT_ATTR = _count
    SCOPE = Local
    START = 0
    -> Sorter_41

Bookmark: Statistics Aggregated by Directory
Stats-Directory_2: StatisticsCalculator
    CALCULATION_MODE = NUMERIC
    FEAT_STATS = transformer_count,NUMERIC_MODE,,,,SUM,,,,,,,,
    GROUP_BY = fme_dataset transformer_type
    SUMMARY -> AttributeRounder_4
    COMPLETE -> Stats-Directory_3
Stats-Directory_3: StatisticsCalculator
    CALCULATION_MODE = NUMERIC
    FEAT_STATS = transformer_count,NUMERIC_MODE,,,,SUM,,,,,,,,
    GROUP_BY = fme_dataset
    SUMMARY -> AttributeManager_12
AttributeManager_12
    ATTR_TABLE = SET_TO transformer_type = Total
    -> AttributeRounder_4
AttributeRounder_4
    PLACES = 0
    ROUND_TYPE = Nearest
    SRC_ATTRS = transformer_count.sum
    -> Sorter_43
Sorter_43
    SORT_PARM = transformer_count.sum NUMERIC DESCENDING
    SORTED -> HTMLReportGenerator_78
HTMLReportGenerator_78
    CONTENT_LIST = HEADER TABLE
    GROUP_BY = fme_dataset
    PAGE_CONFIG = HEADER{{TEXT;Directory: @Value(fme_dataset);HEADER;H5;HEADER_ID;;ALIGNMENT;LEFT;COLOR;0,0,255;FME_CONTROLLER_QUERY_FILE;transformers/dependencies/html5/Header.fme;FME_CONTROLLER_CHOICE;Header}}TABLE{{STYLE;DEFAULT;TABLE;transformer_type|Transformer/transformer_count.sum|Count;FME_CONTROLLER_QUERY_FILE;transformers/dependencies/html5/Table.fme;FME_CONTROLLER_CHOICE;Table}}
    -> HTMLLayouter_47
HTMLLayouter_47
    DIV_STYLE = NONE
    LAYOUT = VERTICAL
    -> HTMLReportGenerator_79
HTMLReportGenerator_79
    CONTENT_LIST = HEADER HTML
    PAGE_CONFIG = HEADER{{TEXT;Transformer Statistics by Directory;HEADER;H3;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_37
Counter_37
    CNT_ATTR = _count
    SCOPE = Local
    START = 1
    -> Sorter_41

FME custom transformer CheckFileExists
Description
This transformer checks if input file paths exist and routes features accordingly.
The transformer supports UNC path, Zip files(*.zip) and wildcards. 
Details
The transformer will check if the filename selected in InputPort exists or not. 
The path can be supplied from a parameter, a network share location, by selecting a filename or using wildcards. 
Notes
Multiple filenames are not supported
Path to file must exist (no missing folders in the path)
FTP paths are not supported
Input
Filename path to check if file exists.   
Parameters
Input ports
Input File Path: Full path to the file to check for existence.  
Output Ports
Exists:Features are output through this port if the file exists.   
_path: The attribute stores the path to the file.  
DoesNotExist:Features are output through this port if the file does not exists.   
_path: This attribute stores the path to the file.

Parameters:
- Input =

Input (input)
    -> ParameterFetcher
ParameterFetcher
    ATTR_LIST = FEC_FullPath {$(Input)}
    -> PythonCaller
Exists (output)
DoesNotExist (output)

Bookmark: Check if File Exists
PythonCaller
    NEW_ATTRIBUTES = _exists
    PYTHONSOURCE:
      import fmeobjects
      import glob
      import zipfile

      def processFeature(feature):

          # Get input path attribute
          fullpath=feature.getAttribute("FEC_FullPath")

          # Check if the file exists
          if glob.glob(fullpath):
              feature.setAttribute("_exists","Yes")
              # if not, try checking inside a zip file
          else:
              fullpath = fullpath.replace("\\","/")
              idx = fullpath.find(".zip")
              if idx > -1:
                  zipPath = fullpath[:idx+4]
                  pathInZip = fullpath[idx+5:]    #i.e. .zip/
                  try:
                      with zipfile.ZipFile(zipPath, 'r') as f:
                          if isinstance(f.getinfo(pathInZip),zipfile.ZipInfo):
                              feature.setAttribute("_exists","Yes")
                              return
                  except (KeyError, FileNotFoundError) as e:
                      pass
                  # not found in a zipfile or in filesystem - does not exist
              else:
                  feature.setAttribute("_exists","No")
    PYTHONSYMBOL = processFeature
    -> AttributeRemover
AttributeRemover
    REMOVE_ATTRS = FEC_FullPath
    -> Tester
Tester
    BOOL_OP = OR
    COMPOSITE_TEST = 1
    TEST_CLAUSE = TEST @Value(_exists) = Yes
    TEST_MODE = TEST
    PASSED -> Exists (output)
    FAILED -> DoesNotExist (output)

FME custom transformer WorkspaceHistory

Parameters:
- FME_BASENAME =
- FME_DATASET =
- HISTORY =
- p_GenerateHistory =
- p_HistoryDescription =

WorkspaceProperties (input)
    -> TST:History_2
WorkspaceHistoryHTML (output)

Bookmark: Workspace History
TST:History_2: Tester
    BOOL_OP = OR
    COMPOSITE_TEST = 1
    TEST_CLAUSE = TEST $(p_GenerateHistory) = YES
    TEST_MODE = TEST
    PASSED -> AttributeCreator_4
AttributeCreator_4
    ATTR_TABLE = SET_TO Directory = @ReplaceRegularExpression(@Value(fme_dataset),"@Value(fme_basename).fm[wx]","",caseSensitive=TRUE)
    -> AttributeKeeper_9
AttributeKeeper_9
    CREATE_BULK_MODE_FEATURES = NO
    KEEP_ATTRS = fme_basename,Directory,history
    -> Tester_2
Tester_2
    BOOL_OP = OR
    COMPOSITE_TEST = 1
    TEST_CLAUSE = TEST history ATTRIBUTE_HAS_A_VALUE ""
    TEST_MODE = TEST
    PASSED -> StringReplacer_11
    FAILED -> Sorter_3
StringReplacer_11
    CASE = NO
    FIND_TEXT = (\d+/\d\d?/\d\d\d?\d?)
    NO_MATCH = _FME_NO_OP_
    REGEXP = YES
    REPLACE_TEXT = <br>\1
    SRC_ATTRS = history
    -> StringReplacer_2
StringReplacer_2
    CASE = NO
    FIND_TEXT = ^<br>
    NO_MATCH = _FME_NO_OP_
    REGEXP = YES
    SRC_ATTRS = history
    -> HTMLReportGenerator_50
Sorter_30
    SORT_PARM = htmlSequence NATURAL ASCENDING
    SORTED -> HTMLLayouter_53
HTMLLayouter_53
    DIV_STYLE = NONE
    LAYOUT = VERTICAL
    -> HTMLReportGenerator_86
HTMLReportGenerator_86
    CONTENT_LIST = HEADER HTML
    PAGE_CONFIG = HEADER{{TEXT;WORKSPACE HISTORY;HEADER;H1;HEADER_ID;;ALIGNMENT;CENTER;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Workspace History
    -> AttributeCreator_30
AttributeCreator_30
    ATTR_TABLE = SET_TO ReportName = WorkspaceHistoryReport.html
    -> WorkspaceHistoryHTML (output)

Bookmark: Extrac History
HTMLReportGenerator_50
    CONTENT_LIST = HEADER TABLE
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}TABLE{{STYLE;BORDERED;TABLE;fme_basename|Workspace/history|Overview;FME_CONTROLLER_QUERY_FILE;transformers/dependencies/html5/Table.fme;FME_CONTROLLER_CHOICE;Table}}
    TITLE = Workspace Descriptions
    -> HTMLLayouter_31
HTMLLayouter_31
    DIV_STYLE = SOLID
    LAYOUT = VERTICAL
    TITLE = Workspace History
    -> HTMLReportGenerator_85
HTMLReportGenerator_85
    CONTENT_LIST = HEADER HTML
    PAGE_CONFIG = HEADER{{TEXT;WORKSPACE HISTORY;HEADER;H2;HEADER_ID;;ALIGNMENT;LEFT;COLOR;0,170,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Workspace overviews
    -> AttributeCreator_29
AttributeCreator_29
    ATTR_TABLE = SET_TO htmlSequence = 3
    -> Sorter_30

Bookmark: Missing History
Sorter_3
    SORT_PARM = Directory NATURAL ASCENDING fme_basename NATURAL ASCENDING
    SORTED -> HTMLReportGenerator_3
HTMLReportGenerator_3
    CONTENT_LIST = HEADER TABLE
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}TABLE{{STYLE;BORDERED;TABLE;fme_basename|Workspace/Directory|Folder;FME_CONTROLLER_QUERY_FILE;transformers/dependencies/html5/Table.fme;FME_CONTROLLER_CHOICE;Table}}
    TITLE = MISSING HISTORY
    -> HTMLLayouter_5
HTMLLayouter_5
    DIV_STYLE = SOLID
    LAYOUT = VERTICAL
    TITLE = MISSING Workspace History
    -> HTMLReportGenerator_7
HTMLReportGenerator_7
    CONTENT_LIST = HEADER HTML
    PAGE_CONFIG = HEADER{{TEXT;MISSING WORKSPACE HISTORY;HEADER;H2;HEADER_ID;;ALIGNMENT;LEFT;COLOR;255,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Workspace History
    -> AttributeCreator_20
AttributeCreator_20
    ATTR_TABLE = SET_TO ReportName = WorkspaceHistoryReport.html
    -> Sorter_30

FME custom transformer IdentifyPathTypes

Parameters:
- FME_BASENAME =
- FME_DATASET =
- TRANSFORMER_ID =
- TRANSFORMER_PARAMETER_NAME =
- TRANSFORMER_TYPE =
- WORKSPACE_ID =
- p_IdentifyFMEParamPAths =
- p_IdentifyNonUNC =
- p_NonUncPaths =
- p_checkExistence_inputs =
- p_checkExistence_ouputs =

Readers (input)
    -> AC:Reader
TransformerParameters (input)
    -> AC:FeatureWriter_3
Transformers (input)
    -> TST:FeatureReader
Transformers_2 (input)
    -> TST:FeatureWriter
Writers (input)
    -> AC:Writer
PathTypesHTML (output)

Bookmark: Identify Non UNC Paths
AC:Reader: AttributeCreator
    ATTR_TABLE = SET_TO _Type = Reader
    -> TST:IdentifyNonUNC
AC:FeatureWriter_3: AttributeCreator
    ATTR_TABLE = SET_TO _Type = Parameters
    -> TST:IdentifyNonUNC
Note: Transformers
TST:FeatureReader: Tester
    BOOL_OP = OR
    COMPOSITE_TEST = 1
    TEST_CLAUSE = TEST @Value(transformer_type) = FeatureReader
    TEST_MODE = TEST
    PASSED -> AC:FeatureReader
AC:FeatureReader: AttributeCreator
    ATTR_TABLE = SET_TO _Type = FeatureReader
    -> TST:IdentifyNonUNC
Note: Transformers
TST:FeatureWriter: Tester
    BOOL_OP = OR
    COMPOSITE_TEST = 1
    TEST_CLAUSE = TEST @Value(transformer_type) = FeatureWriter
    TEST_MODE = TEST
    PASSED -> AC:FeatureWriter
AC:FeatureWriter: AttributeCreator
    ATTR_TABLE = SET_TO _Type = FeatureWriter
    -> TST:IdentifyNonUNC
AC:Writer: AttributeCreator
    ATTR_TABLE = SET_TO _Type = Writer
    -> TST:IdentifyNonUNC
TST:IdentifyNonUNC: Tester
    BOOL_OP = OR
    COMPOSITE_TEST = 1
    TEST_CLAUSE = TEST $(p_IdentifyNonUNC) = YES
    TEST_MODE = TEST
    PASSED -> AttributeCreator_3
AttributeCreator_3
    ATTR_TABLE = SET_TO Directory = @ReplaceRegularExpression(@Value(fme_dataset),"@Value(fme_basename).fm[wx]","",caseSensitive=TRUE)
    -> TestFilter
TestFilter
    DEFAULT_VALUE = <UNFILTERED>
    TEST_LIST = "BOOL_OP,OR,COMPOSITE_TEST,""""""1"""""",TEST_CLAUSE,TEST @Value(_Type) = Reader",Reader,"BOOL_OP,OR,COMPOSITE_TEST,""""""1"""""",TEST_CLAUSE,TEST @Value(_Type) = FeatureReader",FeatureReader,"BOOL_OP,OR,COMPOSITE_TEST,""""""1"""""",TEST_CLAUSE,TEST @Value(_Type) = Parameters",Params,"BOOL_OP,OR,COMPOSITE_TEST,""""""1"""""",TEST_CLAUSE,TEST @Value(_Type) = FeatureWriter",FeatureWriter,"BOOL_OP,OR,COMPOSITE_TEST,""""""1"""""",TEST_CLAUSE,TEST @Value(_Type) = Writer",Writer
    Reader -> AttributeKeeper
    FeatureReader -> AttributeKeeper_3
    Params -> AttributeKeeper_7
    FeatureWriter -> AttributeKeeper_4
    Writer -> AttributeKeeper_2
Note: Normal Reader
AttributeKeeper
    CREATE_BULK_MODE_FEATURES = NO
    KEEP_ATTRS = _Type,Directory,fme_basename,reader_enabled,reader_name,source_dataset
    -> AttributeRenamer_2
AttributeRenamer_2
    ATTR_TABLE:
      RENAME_SET_DEFAULT _Type > Type
      RENAME_SET_DEFAULT source_dataset > Dataset
      RENAME_SET_DEFAULT fme_basename > WorkspaceName
      RENAME_SET_DEFAULT reader_enabled > Enabled
      RENAME_SET_DEFAULT reader_name > TransformerName
    MISSING_INPUT_ATTRS = REMOVE
    -> TST:Input
AttributeKeeper_3
    CREATE_BULK_MODE_FEATURES = NO
    KEEP_ATTRS = _Type,Directory,transformer_id,transformer_name,workspace_id,transformer_enabled
    -> FeatureJoiner_2 [LEFT]
AttributeKeeper_7
    CREATE_BULK_MODE_FEATURES = NO
    KEEP_ATTRS = transformer_id,workspace_id,transformer_parameter_name,transformer_parameter_value,fme_basename
    -> Tester_3
Tester_3
    BOOL_OP = OR
    COMPOSITE_TEST = 1
    TEST_CLAUSE = TEST @Value(transformer_parameter_name) = DATASET
    TEST_MODE = TEST
    PASSED -> FeatureJoiner [RIGHT]
    PASSED -> FeatureJoiner_2 [RIGHT]
FeatureJoiner_2
    ATTR_CONFLICT_RES = Use Left
    GEOMETRY_HANDLING = Use Left
    JOIN_KEYS = transformer_id transformer_id AUTO workspace_id workspace_id AUTO
    JOIN_MODE = Inner
    JOINED -> AttributeRemover
AttributeRemover
    REMOVE_ATTRS = transformer_id,workspace_id,transformer_parameter_name
    -> AttributeRenamer_3
AttributeKeeper_4
    CREATE_BULK_MODE_FEATURES = NO
    KEEP_ATTRS = _Type,Directory,transformer_id,transformer_name,workspace_id,transformer_enabled,fme_basename
    -> FeatureJoiner [LEFT]
FeatureJoiner
    ATTR_CONFLICT_RES = Use Left
    GEOMETRY_HANDLING = Use Left
    JOIN_KEYS = transformer_id transformer_id AUTO workspace_id workspace_id AUTO
    JOIN_MODE = Inner
    JOINED -> AttributeRemover_2
AttributeRemover_2
    REMOVE_ATTRS = transformer_id,workspace_id,transformer_parameter_name
    -> AttributeRenamer_3
AttributeRenamer_3
    ATTR_TABLE:
      RENAME_SET_DEFAULT _Type > Type
      RENAME_SET_DEFAULT transformer_parameter_value > Dataset
      RENAME_SET_DEFAULT fme_basename > WorkspaceName
      RENAME_SET_DEFAULT transformer_enabled > Enabled
      RENAME_SET_DEFAULT transformer_name > TransformerName
    MISSING_INPUT_ATTRS = REMOVE
    -> TST:Input
Note: Normal Writer
AttributeKeeper_2
    CREATE_BULK_MODE_FEATURES = NO
    KEEP_ATTRS = _Type,Directory,fme_basename,writer_enabled,writer_name,destination_dataset
    -> AttributeRenamer
AttributeRenamer
    ATTR_TABLE:
      RENAME_SET_DEFAULT _Type > Type
      RENAME_SET_DEFAULT destination_dataset > Dataset
      RENAME_SET_DEFAULT fme_basename > WorkspaceName
      RENAME_SET_DEFAULT writer_enabled > Enabled
      RENAME_SET_DEFAULT writer_name > TransformerName
    MISSING_INPUT_ATTRS = REMOVE
    -> TST:Input
TST:Input: Tester
    BOOL_OP = OR
    COMPOSITE_TEST = 1
    TEST_CLAUSE = CASE_INSENSITIVE_TEST @Value(Type) CONTAINS Reader
    TEST_MODE = CASE_INSENSITIVE_TEST
    PASSED -> AttributeCreator_8
    FAILED -> AttributeCreator_9
AttributeCreator_8
    ATTR_TABLE = SET_TO dataType = Input
    -> StringReplacer
AttributeCreator_9
    ATTR_TABLE = SET_TO dataType = Output
    -> StringReplacer
StringReplacer
    CASE = NO
    FIND_TEXT = "
    NO_MATCH = _FME_NO_OP_
    REGEXP = NO
    SRC_ATTRS = Dataset
    -> TestFilter_3
TestFilter_3
    DEFAULT_VALUE = <UNFILTERED>
    TEST_LIST = "BOOL_OP,OR,COMPOSITE_TEST,""""""1"""""",TEST_CLAUSE,CASE_INSENSITIVE_TEST @Value(Dataset) BEGINS_WITH $",FME Parameter,"BOOL_OP,OR,COMPOSITE_TEST,""""""1"""""",TEST_CLAUSE,CASE_SENSITIVE_TEST @Value(Dataset) CONTAINS_REGEX ^\w:\\",Local Disk,"BOOL_OP,OR,COMPOSITE_TEST,""""""1"""""",TEST_CLAUSE,CASE_SENSITIVE_TEST @Value(Dataset) CONTAINS_REGEX ^\\\\",UNC,"BOOL_OP,OR,COMPOSITE_TEST,""""""1"""""",TEST_CLAUSE,CASE_SENSITIVE_TEST @Value(Dataset) CONTAINS_REGEX ^http[s]?",URL
    FME Parameter -> AC:FMEParam
    Local Disk -> AC:LocalDisk
    UNC -> AC:UNC
    URL -> AC:URL
TST:IdentifyFMEParams: Tester
    BOOL_OP = OR
    COMPOSITE_TEST = 1
    TEST_CLAUSE = TEST $(p_IdentifyFMEParamPAths) = YES
    TEST_MODE = TEST
    PASSED -> TestFilter_2
TestFilter_2
    DEFAULT_VALUE = Outputs
    TEST_LIST = "BOOL_OP,OR,COMPOSITE_TEST,""""""1"""""",TEST_CLAUSE,TEST @Value(dataType) = Input",Inputs
    Inputs -> TST:Existence_2
    Outputs -> TST:Existence_4
TST:Existence_2: Tester
    BOOL_OP = OR
    COMPOSITE_TEST = 1
    TEST_CLAUSE = TEST $(p_checkExistence_inputs) = YES
    TEST_MODE = TEST
    PASSED -> TestFilter_10
    FAILED -> TestFilter_5
TestFilter_5
    DEFAULT_VALUE = FME Parameter
    TEST_LIST = "BOOL_OP,OR,COMPOSITE_TEST,""""""1"""""",TEST_CLAUSE,CASE_INSENSITIVE_TEST @Value(pathType) = Local Disk",Local Disk,"BOOL_OP,OR,COMPOSITE_TEST,""""""1"""""",TEST_CLAUSE,CASE_INSENSITIVE_TEST @Value(pathType) = UNC",UNC,"BOOL_OP,OR,COMPOSITE_TEST,""""""1"""""",TEST_CLAUSE,TEST @Value(pathType) = URL",URL
    Local Disk -> HTMLReportGenerator_9
    UNC -> HTMLReportGenerator_11
    URL -> HTMLReportGenerator_52
    FME Parameter -> HTMLReportGenerator_12
HTMLReportGenerator_9
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_5
Sorter_5
    SORT_PARM = Directory NATURAL ASCENDING
    SORTED -> HTMLLayouter_6
HTMLLayouter_6
    DIV_STYLE = NONE
    LAYOUT = VERTICAL
    -> HTMLReportGenerator_10
HTMLReportGenerator_10
    CONTENT_LIST = HEADER HTML
    PAGE_CONFIG = HEADER{{TEXT;Local Disk Paths;HEADER;H3;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter
Counter
    CNT_ATTR = _count
    SCOPE = Local
    START = 0
    -> Sorter_8
HTMLReportGenerator_11
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_6
Sorter_6
    SORT_PARM = Directory NATURAL ASCENDING
    SORTED -> HTMLLayouter_7
HTMLLayouter_7
    DIV_STYLE = NONE
    LAYOUT = VERTICAL
    -> HTMLReportGenerator_13
HTMLReportGenerator_13
    CONTENT_LIST = HEADER HTML
    PAGE_CONFIG = HEADER{{TEXT;UNC Paths;HEADER;H3;HEADER_ID;;ALIGNMENT;LEFT;COLOR;0,170,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_2
Counter_2
    CNT_ATTR = _count
    SCOPE = Local
    START = 1
    -> Sorter_8
HTMLReportGenerator_12
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_7
Sorter_7
    SORT_PARM = Directory NATURAL ASCENDING
    SORTED -> HTMLLayouter_8
HTMLLayouter_8
    DIV_STYLE = NONE
    LAYOUT = VERTICAL
    -> HTMLReportGenerator_14
HTMLReportGenerator_14
    CONTENT_LIST = HEADER HTML
    PAGE_CONFIG = HEADER{{TEXT;FME Parameter Paths;HEADER;H3;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_3
Counter_3
    CNT_ATTR = _count
    SCOPE = Local
    START = 3
    -> Sorter_8
HTMLReportGenerator_52
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_31
Sorter_31
    SORT_PARM = Directory NATURAL ASCENDING
    SORTED -> HTMLLayouter_32
HTMLLayouter_32
    DIV_STYLE = NONE
    LAYOUT = VERTICAL
    -> HTMLReportGenerator_53
HTMLReportGenerator_53
    CONTENT_LIST = HEADER HTML
    PAGE_CONFIG = HEADER{{TEXT;URL Paths;HEADER;H3;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_27
Counter_27
    CNT_ATTR = _count
    SCOPE = Local
    START = 2
    -> Sorter_8
Sorter_8
    SORT_PARM = _count NUMERIC ASCENDING
    SORTED -> HTMLLayouter_9
HTMLLayouter_9
    DIV_STYLE = NONE
    LAYOUT = VERTICAL
    -> HTMLReportGenerator_15
HTMLReportGenerator_15
    CONTENT_LIST = HEADER HTML
    PAGE_CONFIG = HEADER{{TEXT;INPUT DATASETS;HEADER;H2;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_21
TestFilter_10
    DEFAULT_VALUE = Check Existence
    TEST_LIST = "BOOL_OP,OR,COMPOSITE_TEST,""""""1"""""",TEST_CLAUSE,TEST @Value(pathType) = URL",URL,"BOOL_OP,OR,COMPOSITE_TEST,""""""1"""""",TEST_CLAUSE,CASE_INSENSITIVE_TEST @Value(pathType) = FME Parameter",FME Parameter
    URL -> HTMLReportGenerator_54
    FME Parameter -> HTMLReportGenerator_26
    Check Existence -> Tester
HTMLReportGenerator_26
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_15
Sorter_15
    SORT_PARM = Directory NATURAL ASCENDING
    SORTED -> HTMLLayouter_16
HTMLLayouter_16
    DIV_STYLE = NONE
    LAYOUT = VERTICAL
    -> HTMLReportGenerator_27
HTMLReportGenerator_27
    CONTENT_LIST = HEADER HTML
    PAGE_CONFIG = HEADER{{TEXT;FME Parameter Paths - Not Checked For Existence;HEADER;H2;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_10
Counter_10
    CNT_ATTR = _count
    SCOPE = Local
    START = 3
    -> Sorter_16
Tester
    BOOL_OP = OR
    COMPOSITE_TEST = 1 OR 2
    TEST_CLAUSE:
      CASE_SENSITIVE_TEST @Value(Dataset) CONTAINS_REGEX  \\\\
      CASE_SENSITIVE_TEST @Value(Dataset) CONTAINS_REGEX \s\w\:\\
    TEST_MODE = TEST
    PASSED -> AttributeSplitter
    FAILED -> CheckFileExists
AttributeSplitter
    ATTR_NAME = Dataset
    DELIMITER = " "
    DROP_EMPTY_PARTS = No
    LIST_NAME = _datasets
    TRIM_OPTION = Both
    -> ListExploder
ListExploder
    ATTR_ACCUM_MODE = Merge List Attributes
    ATTR_CONFLICT_RES = Use List Attribute Values
    INDEX_ATTR = _element_index
    LIST_ATTR = _datasets{}
    ELEMENTS -> AttributeManager
AttributeManager
    ATTR_TABLE:
      REMOVE Dataset
      RENAME_SET_VALUE _datasets > Dataset
      REMOVE _element_index
    -> CheckFileExists
CheckFileExists
    Input = @Value(Dataset)
    Exists -> TestFilter_6
    DoesNotExist -> TestFilter_4
TestFilter_4
    DEFAULT_VALUE = UNC
    TEST_LIST = "BOOL_OP,OR,COMPOSITE_TEST,""""""1"""""",TEST_CLAUSE,CASE_INSENSITIVE_TEST @Value(pathType) = Local Disk",Local Disk
    Local Disk -> HTMLReportGenerator_16
    UNC -> HTMLReportGenerator_18
HTMLReportGenerator_16
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_9
Sorter_9
    SORT_PARM = Directory NATURAL ASCENDING
    SORTED -> HTMLLayouter_10
HTMLLayouter_10
    DIV_STYLE = NONE
    LAYOUT = VERTICAL
    -> HTMLReportGenerator_17
HTMLReportGenerator_17
    CONTENT_LIST = HEADER HTML
    PAGE_CONFIG = HEADER{{TEXT;Local Disk Paths;HEADER;H4;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_4
Counter_4
    CNT_ATTR = _count
    SCOPE = Local
    START = 0
    -> Sorter_11
HTMLReportGenerator_18
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_10
Sorter_10
    SORT_PARM = Directory NATURAL ASCENDING
    SORTED -> HTMLLayouter_11
HTMLLayouter_11
    DIV_STYLE = NONE
    LAYOUT = VERTICAL
    -> HTMLReportGenerator_19
HTMLReportGenerator_19
    CONTENT_LIST = HEADER HTML
    PAGE_CONFIG = HEADER{{TEXT;UNC Paths;HEADER;H4;HEADER_ID;;ALIGNMENT;LEFT;COLOR;0,170,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_5
Counter_5
    CNT_ATTR = _count
    SCOPE = Local
    START = 1
    -> Sorter_11
Sorter_11
    SORT_PARM = _count NUMERIC ASCENDING
    SORTED -> HTMLLayouter_12
HTMLLayouter_12
    DIV_STYLE = NONE
    LAYOUT = VERTICAL
    -> HTMLReportGenerator_20
HTMLReportGenerator_20
    CONTENT_LIST = HEADER HTML
    PAGE_CONFIG = HEADER{{TEXT;NON-EXISTENT DATASETS;HEADER;H3;HEADER_ID;;ALIGNMENT;LEFT;COLOR;170,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_6
Counter_6
    CNT_ATTR = _count
    SCOPE = Local
    START = 0
    -> Sorter_16
TestFilter_6
    DEFAULT_VALUE = FME Parameter
    TEST_LIST = "BOOL_OP,OR,COMPOSITE_TEST,""""""1"""""",TEST_CLAUSE,CASE_INSENSITIVE_TEST @Value(pathType) = Local Disk",Local Disk,"BOOL_OP,OR,COMPOSITE_TEST,""""""1"""""",TEST_CLAUSE,CASE_INSENSITIVE_TEST @Value(pathType) = UNC",UNC
    Local Disk -> HTMLReportGenerator_21
    UNC -> HTMLReportGenerator_23
HTMLReportGenerator_21
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_12
Sorter_12
    SORT_PARM = Directory NATURAL ASCENDING
    SORTED -> HTMLLayouter_13
HTMLLayouter_13
    DIV_STYLE = NONE
    LAYOUT = VERTICAL
    -> HTMLReportGenerator_22
HTMLReportGenerator_22
    CONTENT_LIST = HEADER HTML
    PAGE_CONFIG = HEADER{{TEXT;Local Disk Paths;HEADER;H4;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_7
Counter_7
    CNT_ATTR = _count
    SCOPE = Local
    START = 0
    -> Sorter_14
HTMLReportGenerator_23
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_13
Sorter_13
    SORT_PARM = Directory NATURAL ASCENDING
    SORTED -> HTMLLayouter_14
HTMLLayouter_14
    DIV_STYLE = NONE
    LAYOUT = VERTICAL
    -> HTMLReportGenerator_24
HTMLReportGenerator_24
    CONTENT_LIST = HEADER HTML
    PAGE_CONFIG = HEADER{{TEXT;UNC Paths;HEADER;H4;HEADER_ID;;ALIGNMENT;LEFT;COLOR;0,170,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_8
Counter_8
    CNT_ATTR = _count
    SCOPE = Local
    START = 1
    -> Sorter_14
Sorter_14
    SORT_PARM = _count NUMERIC ASCENDING
    SORTED -> HTMLLayouter_15
HTMLLayouter_15
    DIV_STYLE = NONE
    LAYOUT = VERTICAL
    -> HTMLReportGenerator_25
HTMLReportGenerator_25
    CONTENT_LIST = HEADER HTML
    PAGE_CONFIG = HEADER{{TEXT;EXISTING DATASETS;HEADER;H3;HEADER_ID;;ALIGNMENT;LEFT;COLOR;0,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_9
Counter_9
    CNT_ATTR = _count
    SCOPE = Local
    START = 1
    -> Sorter_16
HTMLReportGenerator_54
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_32
Sorter_32
    SORT_PARM = Directory NATURAL ASCENDING
    SORTED -> HTMLLayouter_33
HTMLLayouter_33
    DIV_STYLE = NONE
    LAYOUT = VERTICAL
    -> HTMLReportGenerator_55
HTMLReportGenerator_55
    CONTENT_LIST = HEADER HTML
    PAGE_CONFIG = HEADER{{TEXT;URL Paths - Not Checked For Existence;HEADER;H2;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_28
Counter_28
    CNT_ATTR = _count
    SCOPE = Local
    START = 2
    -> Sorter_16
Sorter_16
    SORT_PARM = _count NUMERIC ASCENDING
    SORTED -> HTMLLayouter_17
HTMLLayouter_17
    DIV_STYLE = NONE
    LAYOUT = VERTICAL
    -> HTMLReportGenerator_28
HTMLReportGenerator_28
    CONTENT_LIST = HEADER HTML
    PAGE_CONFIG = HEADER{{TEXT;INPUT DATASETS;HEADER;H2;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_21
Counter_21
    CNT_ATTR = _count
    SCOPE = Local
    START = 0
    -> Sorter_29
TST:Existence_4: Tester
    BOOL_OP = OR
    COMPOSITE_TEST = 1
    TEST_CLAUSE = TEST $(p_checkExistence_ouputs) = YES
    TEST_MODE = TEST
    PASSED -> TestFilter_12
    FAILED -> TestFilter_11
TestFilter_11
    DEFAULT_VALUE = FME Parameter
    TEST_LIST = "BOOL_OP,OR,COMPOSITE_TEST,""""""1"""""",TEST_CLAUSE,CASE_INSENSITIVE_TEST @Value(pathType) = Local Disk",Local Disk,"BOOL_OP,OR,COMPOSITE_TEST,""""""1"""""",TEST_CLAUSE,CASE_INSENSITIVE_TEST @Value(pathType) = UNC",UNC,"BOOL_OP,OR,COMPOSITE_TEST,""""""1"""""",TEST_CLAUSE,TEST @Value(pathType) = URL",URL
    Local Disk -> HTMLReportGenerator_29
    UNC -> HTMLReportGenerator_31
    URL -> HTMLReportGenerator_56
    FME Parameter -> HTMLReportGenerator_32
HTMLReportGenerator_29
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_17
Sorter_17
    SORT_PARM = Directory NATURAL ASCENDING
    SORTED -> HTMLLayouter_18
HTMLLayouter_18
    DIV_STYLE = NONE
    LAYOUT = VERTICAL
    -> HTMLReportGenerator_30
HTMLReportGenerator_30
    CONTENT_LIST = HEADER HTML
    PAGE_CONFIG = HEADER{{TEXT;Local Disk Paths;HEADER;H3;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_11
Counter_11
    CNT_ATTR = _count
    SCOPE = Local
    START = 0
    -> Sorter_20
HTMLReportGenerator_31
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_18
Sorter_18
    SORT_PARM = Directory NATURAL ASCENDING
    SORTED -> HTMLLayouter_19
HTMLLayouter_19
    DIV_STYLE = NONE
    LAYOUT = VERTICAL
    -> HTMLReportGenerator_33
HTMLReportGenerator_33
    CONTENT_LIST = HEADER HTML
    PAGE_CONFIG = HEADER{{TEXT;UNC Paths;HEADER;H3;HEADER_ID;;ALIGNMENT;LEFT;COLOR;0,170,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_12
Counter_12
    CNT_ATTR = _count
    SCOPE = Local
    START = 1
    -> Sorter_20
HTMLReportGenerator_32
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_19
Sorter_19
    SORT_PARM = Directory NATURAL ASCENDING
    SORTED -> HTMLLayouter_20
HTMLLayouter_20
    DIV_STYLE = NONE
    LAYOUT = VERTICAL
    -> HTMLReportGenerator_34
HTMLReportGenerator_34
    CONTENT_LIST = HEADER HTML
    PAGE_CONFIG = HEADER{{TEXT;FME Parameter Paths;HEADER;H3;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_13
Counter_13
    CNT_ATTR = _count
    SCOPE = Local
    START = 3
    -> Sorter_20
HTMLReportGenerator_56
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_33
Sorter_33
    SORT_PARM = Directory NATURAL ASCENDING
    SORTED -> HTMLLayouter_34
HTMLLayouter_34
    DIV_STYLE = NONE
    LAYOUT = VERTICAL
    -> HTMLReportGenerator_57
HTMLReportGenerator_57
    CONTENT_LIST = HEADER HTML
    PAGE_CONFIG = HEADER{{TEXT;URL Paths;HEADER;H3;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_29
Counter_29
    CNT_ATTR = _count
    SCOPE = Local
    START = 2
    -> Sorter_20
Sorter_20
    SORT_PARM = _count NUMERIC ASCENDING
    SORTED -> HTMLLayouter_21
HTMLLayouter_21
    DIV_STYLE = NONE
    LAYOUT = VERTICAL
    -> HTMLReportGenerator_35
HTMLReportGenerator_35
    CONTENT_LIST = HEADER HTML
    PAGE_CONFIG = HEADER{{TEXT;OUTPUT DATASETS;HEADER;H2;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_22
TestFilter_12
    DEFAULT_VALUE = Check Existence
    TEST_LIST = "BOOL_OP,OR,COMPOSITE_TEST,""""""1"""""",TEST_CLAUSE,TEST @Value(pathType) = URL",URL,"BOOL_OP,OR,COMPOSITE_TEST,""""""1"""""",TEST_CLAUSE,CASE_INSENSITIVE_TEST @Value(pathType) = FME Parameter",FME Parameter
    URL -> HTMLReportGenerator_58
    FME Parameter -> HTMLReportGenerator_46
    Check Existence -> Tester_5
HTMLReportGenerator_46
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_27
Sorter_27
    SORT_PARM = Directory NATURAL ASCENDING
    SORTED -> HTMLLayouter_28
HTMLLayouter_28
    DIV_STYLE = NONE
    LAYOUT = VERTICAL
    -> HTMLReportGenerator_47
HTMLReportGenerator_47
    CONTENT_LIST = HEADER HTML
    PAGE_CONFIG = HEADER{{TEXT;FME Parameter Paths - Not Checked For Existence;HEADER;H4;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_20
Counter_20
    CNT_ATTR = _count
    SCOPE = Local
    START = 3
    -> Sorter_28
HTMLReportGenerator_58
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_34
Sorter_34
    SORT_PARM = Directory NATURAL ASCENDING
    SORTED -> HTMLLayouter_35
HTMLLayouter_35
    DIV_STYLE = NONE
    LAYOUT = VERTICAL
    -> HTMLReportGenerator_59
HTMLReportGenerator_59
    CONTENT_LIST = HEADER HTML
    PAGE_CONFIG = HEADER{{TEXT;URL Paths - Not Checked For Existence;HEADER;H4;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_30
Counter_30
    CNT_ATTR = _count
    SCOPE = Local
    START = 2
    -> Sorter_28
Tester_5
    BOOL_OP = OR
    COMPOSITE_TEST = 1 OR 2
    TEST_CLAUSE:
      CASE_SENSITIVE_TEST @Value(Dataset) CONTAINS_REGEX  \\\\
      CASE_SENSITIVE_TEST @Value(Dataset) CONTAINS_REGEX \s\w\:\\
    TEST_MODE = TEST
    PASSED -> AttributeSplitter_2
    FAILED -> CheckFileExists_2
AttributeSplitter_2
    ATTR_NAME = Dataset
    DELIMITER = " "
    DROP_EMPTY_PARTS = No
    LIST_NAME = _datasets
    TRIM_OPTION = Both
    -> ListExploder_2
ListExploder_2
    ATTR_ACCUM_MODE = Merge List Attributes
    ATTR_CONFLICT_RES = Use List Attribute Values
    INDEX_ATTR = _element_index
    LIST_ATTR = _datasets{}
    ELEMENTS -> AttributeManager_4
AttributeManager_4
    ATTR_TABLE:
      REMOVE Dataset
      RENAME_SET_VALUE _datasets > Dataset
      REMOVE _element_index
    -> CheckFileExists_2
CheckFileExists_2
    Input = @Value(Dataset)
    Exists -> TestFilter_9
    DoesNotExist -> TestFilter_8
TestFilter_8
    DEFAULT_VALUE = UNC
    TEST_LIST = "BOOL_OP,OR,COMPOSITE_TEST,""""""1"""""",TEST_CLAUSE,CASE_INSENSITIVE_TEST @Value(pathType) = Local Disk",Local Disk
    Local Disk -> HTMLReportGenerator_36
    UNC -> HTMLReportGenerator_38
HTMLReportGenerator_36
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_21
Sorter_21
    SORT_PARM = Directory NATURAL ASCENDING
    SORTED -> HTMLLayouter_22
HTMLLayouter_22
    DIV_STYLE = NONE
    LAYOUT = VERTICAL
    -> HTMLReportGenerator_37
HTMLReportGenerator_37
    CONTENT_LIST = HEADER HTML
    PAGE_CONFIG = HEADER{{TEXT;Local Disk Paths;HEADER;H4;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_14
Counter_14
    CNT_ATTR = _count
    SCOPE = Local
    START = 0
    -> Sorter_23
HTMLReportGenerator_38
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_22
Sorter_22
    SORT_PARM = Directory NATURAL ASCENDING
    SORTED -> HTMLLayouter_23
HTMLLayouter_23
    DIV_STYLE = NONE
    LAYOUT = VERTICAL
    -> HTMLReportGenerator_39
HTMLReportGenerator_39
    CONTENT_LIST = HEADER HTML
    PAGE_CONFIG = HEADER{{TEXT;UNC Paths;HEADER;H4;HEADER_ID;;ALIGNMENT;LEFT;COLOR;0,170,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_15
Counter_15
    CNT_ATTR = _count
    SCOPE = Local
    START = 1
    -> Sorter_23
Sorter_23
    SORT_PARM = _count NUMERIC ASCENDING
    SORTED -> HTMLLayouter_24
HTMLLayouter_24
    DIV_STYLE = NONE
    LAYOUT = VERTICAL
    -> HTMLReportGenerator_40
HTMLReportGenerator_40
    CONTENT_LIST = HEADER HTML
    PAGE_CONFIG = HEADER{{TEXT;NON-EXISTENT DATASETS;HEADER;H3;HEADER_ID;;ALIGNMENT;LEFT;COLOR;170,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_18
Counter_18
    CNT_ATTR = _count
    SCOPE = Local
    START = 0
    -> Sorter_28
TestFilter_9
    DEFAULT_VALUE = FME Parameter
    TEST_LIST = "BOOL_OP,OR,COMPOSITE_TEST,""""""1"""""",TEST_CLAUSE,CASE_INSENSITIVE_TEST @Value(pathType) = Local Disk",Local Disk,"BOOL_OP,OR,COMPOSITE_TEST,""""""1"""""",TEST_CLAUSE,CASE_INSENSITIVE_TEST @Value(pathType) = UNC",UNC
    Local Disk -> HTMLReportGenerator_41
    UNC -> HTMLReportGenerator_43
HTMLReportGenerator_41
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_24
Sorter_24
    SORT_PARM = Directory NATURAL ASCENDING
    SORTED -> HTMLLayouter_25
HTMLLayouter_25
    DIV_STYLE = NONE
    LAYOUT = VERTICAL
    -> HTMLReportGenerator_42
HTMLReportGenerator_42
    CONTENT_LIST = HEADER HTML
    PAGE_CONFIG = HEADER{{TEXT;Local Disk Paths;HEADER;H4;HEADER_ID;;ALIGNMENT;LEFT;COLOR;255,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_16
Counter_16
    CNT_ATTR = _count
    SCOPE = Local
    START = 0
    -> Sorter_26
HTMLReportGenerator_43
    CONTENT_LIST = HEADER TABLE
    GROUP_BY = Directory
    PAGE_CONFIG = HEADER{{TEXT;Directory: @Value(Directory);HEADER;H4;HEADER_ID;;ALIGNMENT;LEFT;COLOR;0,0,255;FME_CONTROLLER_QUERY_FILE;transformers/dependencies/html5/Header.fme;FME_CONTROLLER_CHOICE;Header}}TABLE{{STYLE;DEFAULT;TABLE;WorkspaceName|Workspace Name/TransformerName|Transformer Name/Type|Transformer Type/Dataset|Dataset;FME_CONTROLLER_QUERY_FILE;transformers/dependencies/html5/Table.fme;FME_CONTROLLER_CHOICE;Table}}
    -> Sorter_25
Sorter_25
    SORT_PARM = Directory NATURAL ASCENDING
    SORTED -> HTMLLayouter_26
HTMLLayouter_26
    DIV_STYLE = NONE
    LAYOUT = VERTICAL
    -> HTMLReportGenerator_44
HTMLReportGenerator_44
    CONTENT_LIST = HEADER HTML
    PAGE_CONFIG = HEADER{{TEXT;UNC Paths;HEADER;H4;HEADER_ID;;ALIGNMENT;LEFT;COLOR;0,170,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_17
Counter_17
    CNT_ATTR = _count
    SCOPE = Local
    START = 1
    -> Sorter_26
Sorter_26
    SORT_PARM = _count NUMERIC ASCENDING
    SORTED -> HTMLLayouter_27
HTMLLayouter_27
    DIV_STYLE = NONE
    LAYOUT = VERTICAL
    -> HTMLReportGenerator_45
HTMLReportGenerator_45
    CONTENT_LIST = HEADER HTML
    PAGE_CONFIG = HEADER{{TEXT;EXISTING DATASETS;HEADER;H3;HEADER_ID;;ALIGNMENT;LEFT;COLOR;0,85,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_19
Counter_19
    CNT_ATTR = _count
    SCOPE = Local
    START = 1
    -> Sorter_28
Sorter_28
    SORT_PARM = _count NUMERIC ASCENDING
    SORTED -> HTMLLayouter_29
HTMLLayouter_29
    DIV_STYLE = NONE
    LAYOUT = VERTICAL
    -> HTMLReportGenerator_48
HTMLReportGenerator_48
    CONTENT_LIST = HEADER HTML
    PAGE_CONFIG = HEADER{{TEXT;OUTPUT DATASETS;HEADER;H2;HEADER_ID;;ALIGNMENT;LEFT;COLOR;0,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> Counter_22
Counter_22
    CNT_ATTR = _count
    SCOPE = Local
    START = 1
    -> Sorter_29
Sorter_29
    SORT_PARM = _count NUMERIC ASCENDING
    SORTED -> HTMLLayouter_30
HTMLLayouter_30
    DIV_STYLE = SOLID
    LAYOUT = VERTICAL
    -> HTMLReportGenerator_49
HTMLReportGenerator_49
    CONTENT_LIST = HEADER SEPARATOR HTML
    PAGE_CONFIG = HEADER{{TEXT;INPUT/OUTPUT DATA PATH REPORTING;HEADER;H2;HEADER_ID;;ALIGNMENT;CENTER;COLOR;255,0,0;FME_CONTROLLER_QUERY_FILE;transformers/dependencies/html5/Header.fme;FME_CONTROLLER_CHOICE;Header}}SEPARATOR{{WIDTH;3;FME_CONTROLLER_QUERY_FILE;transformers/dependencies/html5/Separator.fme;FME_CONTROLLER_CHOICE;Separator}}HTML{{HTML;@Value(html_content);FME_CONTROLLER_QUERY_FILE;transformers/dependencies/html5/Custom HTML.fme;FME_CONTROLLER_CHOICE;Custom HTML}}
    TITLE = I/O Paths
    -> AttributeCreator_19
AttributeCreator_19
    ATTR_TABLE = SET_TO ReportName = InputOutputPATHS.html
    -> PathTypesHTML (output)

Bookmark: Assign Path Type
AC:LocalDisk: AttributeCreator
    ATTR_TABLE = SET_TO pathType = Local Disk
    -> TestFilter_2
AC:UNC: AttributeCreator
    ATTR_TABLE = SET_TO pathType = UNC
    -> TestFilter_2
AC:URL: AttributeCreator
    ATTR_TABLE = SET_TO pathType = URL
    -> TestFilter_2
AC:FMEParam: AttributeCreator
    ATTR_TABLE = SET_TO pathType = FME Parameter
    -> TST:IdentifyFMEParams

FME custom transformer ListCustomTransformers

Parameters:
- CUSTOM_TRANSFORMER_PARENT_NAME =
- FME_BASENAME =
- FME_DATASET =
- TRANSFORMER_TYPE =
- p_Transformers =
- p_customXformer =
- p_customXformerGroup =
- p_customXformerWildcard =

Transformers (input)
    -> Junction_10
CustomTransformersHTML (output)

Bookmark: List Custom Transformers
Note: Transformers
Junction_10
    -> TST-CTList
TST-CTList: Tester
    BOOL_OP = OR
    COMPOSITE_TEST = 1
    TEST_CLAUSE = TEST $(p_customXformer) = YES
    TEST_MODE = TEST
    PASSED -> TST:ExternalXformer
TST:ExternalXformer: Tester
    BOOL_OP = OR
    COMPOSITE_TEST = 1
    TEST_CLAUSE = TEST @Value(transformer_type) = ExternalTransformer
    TEST_MODE = TEST
    PASSED -> AttributeKeeper_8
    FAILED -> TST-EMBEDED-CT
TST-EMBEDED-CT: Tester
    BOOL_OP = OR
    COMPOSITE_TEST = 1
    TEST_CLAUSE = TEST custom_transformer_parent_name ATTRIBUTE_HAS_A_VALUE ""
    TEST_MODE = TEST
    PASSED -> DuplicateFilter_4
DuplicateFilter_4
    INPUT_ORDERED_CHOICE = No
    KEYATTR = fme_dataset custom_transformer_parent_name
    UNIQUE -> AttributeKeeper_10
AttributeKeeper_10
    CREATE_BULK_MODE_FEATURES = NO
    KEEP_ATTRS = custom_transformer_parent_name,fme_dataset,fme_basename
    -> AttributeManager_2
AttributeManager_2
    ATTR_TABLE:
      RENAME_SET_VALUE custom_transformer_parent_name > Transformer Name
      SET_TO Directory = @ReplaceRegularExpression(@Value(fme_dataset),"@Value(fme_basename).fm[wx]","",caseSensitive=TRUE)
      RENAME_SET_VALUE fme_basename > Workspace
      SET_TO Transformer Type = Embedded
      REMOVE fme_dataset
    -> StringSearcher_13
AttributeKeeper_8
    CREATE_BULK_MODE_FEATURES = NO
    KEEP_ATTRS = transformer_name,fme_dataset,fme_basename
    -> AttributeManager_3
AttributeManager_3
    ATTR_TABLE:
      RENAME_SET_VALUE transformer_name > Transformer Name
      SET_TO Directory = @ReplaceRegularExpression(@Value(fme_dataset),"@Value(fme_basename).fm[wx]","",caseSensitive=TRUE)
      RENAME_SET_VALUE fme_basename > Workspace
      SET_TO Transformer Type = Linked
      REMOVE fme_dataset
    -> StringSearcher_13
StringSearcher_13
    CASE = no
    MATCHED_RESULT_ATTR = _first_match
    REGEXP = $(p_customXformerWildcard)
    STRING_TO_SEARCH = @Value(Transformer Name)
    MATCHED -> Sorter_35
Sorter_35
    SORT_PARM = Directory ALPHA ASCENDING "Transformer Type" ALPHA ASCENDING
    SORTED -> HTMLReportGenerator_60
HTMLReportGenerator_60
    CONTENT_LIST = HEADER TABLE
    GROUP_BY = Directory Workspace
    PAGE_CONFIG = HEADER{{TEXT;- Workspace: @Value(Workspace);HEADER;H6;HEADER_ID;;ALIGNMENT;LEFT;COLOR;0,0,0;FME_CONTROLLER_QUERY_FILE;transformers/dependencies/html5/Header.fme;FME_CONTROLLER_CHOICE;Header}}TABLE{{STYLE;DEFAULT;TABLE;Transformer Type|Transformer Type/Transformer Name|Transformer Name;FME_CONTROLLER_QUERY_FILE;transformers/dependencies/html5/Table.fme;FME_CONTROLLER_CHOICE;Table}}
    -> HTMLLayouter_36
HTMLLayouter_36
    DIV_STYLE = NONE
    GROUP_BY = Directory
    LAYOUT = VERTICAL
    -> HTMLReportGenerator_61
HTMLReportGenerator_61
    CONTENT_LIST = HEADER HTML
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    -> HTMLLayouter_37
HTMLLayouter_37
    DIV_STYLE = SOLID
    LAYOUT = VERTICAL
    -> StringReplacer_2
StringReplacer_2
    CASE = NO
    FIND_TEXT = <td>Embedded</td>
    NO_MATCH = _FME_NO_OP_
    REGEXP = NO
    REPLACE_TEXT = <td style="color:orange"><b>Embedded</b></td>
    SRC_ATTRS = html_content
    -> AttributeCreator_28
AttributeCreator_28
    ATTR_TABLE = SET_TO heading = Linked & Embedded Custom Transformer Reporting
    -> HTMLReportGenerator_62
HTMLReportGenerator_62
    CONTENT_LIST = HEADER HTML
    PAGE_CONFIG = HEADER{{TEXT;@Value(heading);HEADER;H2;HEADER_ID;;ALIGNMENT;CENTER;COLOR;255,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Custom Transformers
    -> AttributeCreator_23
AttributeCreator_23
    ATTR_TABLE = SET_TO ReportName = CustomTransformersReport.html
    -> CustomTransformersHTML (output)

FME custom transformer AttributeNameSearch

Parameters:
- FEATURE_TYPE_ID =
- TRANSFORMER_ID =
- USER_ATTRIBUTE_TYPE =
- WORKSPACE_ID =
- p_attrSearch_Reader =
- p_attrSearch_Transformer =
- p_attrSearch_Writer =
- p_attrSearch_wildcard =
- p_attributeSearch_2 =
- p_wildcardSearches =

WriterFeatureTypes (input)
    -> Tester_23
FeatureTypeUserAttributes (input)
    -> FeatureJoiner_4 [RIGHT]
FeatureTypeUserAttributes_2 (input)
    -> FeatureJoiner_10 [RIGHT]
ReaderFeatureTypes (input)
    -> Tester_22
transformerfeaturetype (input)
    -> AttributeManager_16
Transformers (input)
    -> Tester_21
AttributeNamesHTML (output)

Bookmark: Search Attribute Names
Tester_23
    BOOL_OP = OR
    COMPOSITE_TEST = 1
    TEST_CLAUSE = TEST $(p_attrSearch_Writer) = YES
    TEST_MODE = TEST
    PASSED -> FeatureJoiner_4 [LEFT]
FeatureJoiner_4
    ATTR_CONFLICT_RES = Use Left
    GEOMETRY_HANDLING = Use Left
    JOIN_KEYS = feature_type_id feature_type_id AUTO workspace_id workspace_id AUTO
    JOIN_MODE = Inner
    JOINED -> AttributeManager_19
AttributeManager_19
    ATTR_TABLE:
      RENAME_SET_VALUE fme_basename > Workspace
      SET_TO Type = Writer
      RENAME_SET_VALUE writer_id > Transformer Name
      RENAME_SET_VALUE user_attribute_name > Attribute Name = FME_CONDITIONAL:DEFAULT_VALUE'_FME_NO_OP_'BOOL_OP;OR;COMPOSITE_TEST;1;TEST user_attribute_type ATTRIBUTE_HAS_A_VALUE _FME_BLANK_STRING_'@Value(Attribute Name) (@Value(user_attribute_type))'FME_NUM_CONDITIONS2___
      REMOVE workspace_id
      REMOVE feature_type_id
      REMOVE writer_feature_type_qualifier
      REMOVE writer_feature_type_name
      REMOVE writer_feature_type_possible_geometries
      REMOVE writer_feature_type_enabled
      REMOVE fme_geometry{0}
      RENAME_SET_VALUE fme_dataset > Directory = @ReplaceRegularExpression(@Value(Directory),@Value(Workspace).fm[wx],,caseSensitive=TRUE)
      REMOVE fme_feature_type
      REMOVE user_attribute_type
      REMOVE user_attribute_exposed
      REMOVE fme_geometry{}
    -> Junction_29
Tester_22
    BOOL_OP = OR
    COMPOSITE_TEST = 1
    TEST_CLAUSE = TEST $(p_attrSearch_Reader) = YES
    TEST_MODE = TEST
    PASSED -> FeatureJoiner_10 [LEFT]
FeatureJoiner_10
    ATTR_CONFLICT_RES = Use Left
    GEOMETRY_HANDLING = Use Left
    JOIN_KEYS = feature_type_id feature_type_id AUTO workspace_id workspace_id AUTO
    JOIN_MODE = Inner
    JOINED -> AttributeManager_17
AttributeManager_17
    ATTR_TABLE:
      RENAME_SET_VALUE fme_basename > Workspace
      SET_TO Type = Reader
      REMOVE workspace_id
      RENAME_SET_VALUE reader_id > Transformer Name
      RENAME_SET_VALUE user_attribute_name > Attribute Name = FME_CONDITIONAL:DEFAULT_VALUE'_FME_NO_OP_'BOOL_OP;OR;COMPOSITE_TEST;1;TEST user_attribute_type ATTRIBUTE_HAS_A_VALUE _FME_BLANK_STRING_'@Value(Attribute Name) (@Value(user_attribute_type))'FME_NUM_CONDITIONS2___
      REMOVE feature_type_id
      REMOVE reader_feature_type_name
      REMOVE reader_feature_type_qualifier
      REMOVE reader_feature_type_possible_geometries
      REMOVE reader_feature_type_enabled
      RENAME_SET_VALUE fme_dataset > Directory = @ReplaceRegularExpression(@Value(Directory),@Value(Workspace).fm[wx],,caseSensitive=TRUE)
      REMOVE fme_feature_type
      REMOVE user_attribute_type
      REMOVE user_attribute_exposed
      REMOVE fme_geometry{}
    -> Junction_29
AttributeManager_16
    ATTR_TABLE:
      SET_TO Type = Transformer
      REMOVE transformer_output_port_id
      REMOVE transformer_output_port_attribute_constant_value
      REMOVE transformer_output_port_attribute_enabled
      REMOVE fme_feature_type
      REMOVE fme_geometry{}
    -> FeatureJoiner_11 [LEFT]
Tester_21
    BOOL_OP = OR
    COMPOSITE_TEST = 1
    TEST_CLAUSE = TEST $(p_attrSearch_Transformer) = YES
    TEST_MODE = TEST
    PASSED -> AttributeKeeper_5
AttributeKeeper_5
    CREATE_BULK_MODE_FEATURES = NO
    KEEP_ATTRS = transformer_id,transformer_name,workspace_id
    -> FeatureJoiner_11 [RIGHT]
FeatureJoiner_11
    ATTR_CONFLICT_RES = Use Left
    GEOMETRY_HANDLING = Use Left
    JOIN_KEYS = workspace_id workspace_id AUTO transformer_id transformer_id AUTO
    JOIN_MODE = Inner
    JOINED -> AttributeManager_18
AttributeManager_18
    ATTR_TABLE:
      RENAME_SET_VALUE fme_basename > Workspace
      RENAME_SET_VALUE transformer_name > Transformer Name = FME_CONDITIONAL:DEFAULT_VALUE'_FME_NO_OP_'BOOL_OP;OR;COMPOSITE_TEST;1;TEST custom_transformer_parent_name ATTRIBUTE_HAS_A_VALUE _FME_BLANK_STRING_'@Value(Transformer Name) (@Value(custom_transformer_parent_name))'FME_NUM_CONDITIONS2___
      RENAME_SET_VALUE transformer_output_port_attribute_name > Attribute Name
      REMOVE workspace_id
      REMOVE transformer_id
      RENAME_SET_VALUE fme_dataset > Directory = @ReplaceRegularExpression(@Value(Directory),@Value(Workspace).fm[wx],,caseSensitive=TRUE)
      REMOVE custom_transformer_parent_name
    -> Junction_29
Junction_29
    -> StringSearcher_8
StringSearcher_8
    CASE = no
    MATCHED_RESULT_ATTR = _first_match
    REGEXP = $(p_attrSearch_wildcard)
    STRING_TO_SEARCH = @Value(Attribute Name)
    MATCHED -> HTMLReportGenerator_8
HTMLReportGenerator_8
    CONTENT_LIST = HEADER TABLE
    GROUP_BY = Directory Workspace
    PAGE_CONFIG = HEADER{{TEXT;Workspace: @Value(Workspace);HEADER;H6;HEADER_ID;;ALIGNMENT;LEFT;COLOR;0,0,255;FME_CONTROLLER_QUERY_FILE;transformers/dependencies/html5/Header.fme;FME_CONTROLLER_CHOICE;Header}}TABLE{{STYLE;BORDERED;TABLE;Type|Type/Transformer Name|Transformer Name/Attribute Name|Attribute Name;FME_CONTROLLER_QUERY_FILE;transformers/dependencies/html5/Table.fme;FME_CONTROLLER_CHOICE;Table}}
    -> HTMLLayouter_49
HTMLLayouter_49
    DIV_STYLE = SOLID
    GROUP_BY = Directory
    LAYOUT = VERTICAL
    -> HTMLReportGenerator_81
HTMLReportGenerator_81
    CONTENT_LIST = HEADER HTML
    GROUP_BY = Directory
    PAGE_CONFIG = HEADER{{TEXT;Directory: @Value(Directory);HEADER;H5;HEADER_ID;;ALIGNMENT;LEFT;COLOR;0,0,255;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = MISSING DESCRIPTIONS
    -> HTMLLayouter
HTMLLayouter
    DIV_STYLE = NONE
    LAYOUT = VERTICAL
    -> HTMLReportGenerator
HTMLReportGenerator
    CONTENT_LIST = HEADER HTML
    PAGE_CONFIG = HEADER{{TEXT;Attribute Search;HEADER;H2;HEADER_ID;;ALIGNMENT;CENTER;COLOR;255,0,0;FME_CONTROLLER_QUERY_FILE;transformers/dependencies/html5/Header.fme;FME_CONTROLLER_CHOICE;Header}}HTML{{HTML;@Value(html_content);FME_CONTROLLER_QUERY_FILE;transformers/dependencies/html5/Custom HTML.fme;FME_CONTROLLER_CHOICE;Custom HTML}}
    TITLE = Attribute Search
    -> AttributeCreator_18
AttributeCreator_18
    ATTR_TABLE = SET_TO ReportName = AttributeNameTypeSearch.html
    -> AttributeNamesHTML (output)
